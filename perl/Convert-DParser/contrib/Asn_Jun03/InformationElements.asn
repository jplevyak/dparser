InformationElements DEFINITIONS AUTOMATIC TAGS ::=

-- ***************************************************
--
--     CORE NETWORK INFORMATION ELEMENTS (10.3.1)
--
-- ***************************************************

BEGIN

IMPORTS

	hiPDSCHidentities,
	hiPUSCHidentities,
	hiRM,
	maxAC,
	maxAdditionalMeas,
	maxASC,
	maxASCmap,
	maxASCpersist,
	maxCCTrCH,
	maxCellMeas,
	maxCellMeas-1,
	maxCNdomains,
	maxCPCHsets,
	maxDPCH-DLchan,
	maxDPDCH-UL,
	maxDRACclasses,
	maxFACHPCH,
	maxFreq,
	maxFreqBandsFDD,
	maxFreqBandsTDD,
	maxFreqBandsGSM,
	maxInterSysMessages,
	maxLoCHperRLC,
	maxMeasEvent,
	maxMeasIntervals,
	maxMeasParEvent,
	maxNumCDMA2000Freqs,
	maxNumFDDFreqs,
	maxNumGSMFreqRanges,
	maxNumTDDFreqs,
	maxOtherRAT,
	maxOtherRAT-16,
	maxPage1,
	maxPCPCH-APsig,
	maxPCPCH-APsubCh,
	maxPCPCH-CDsig,
	maxPCPCH-CDsubCh,
	maxPCPCH-SF,
	maxPCPCHs,
	maxPDCPAlgoType,
	maxPDSCH,
	maxPDSCH-TFCIgroups,
	maxPRACH,
	maxPredefConfig,
	maxPUSCH,
	maxRABsetup,
	maxRAT,
	maxRB,
	maxRBallRABs,
	maxRBMuxOptions,
	maxRBperRAB,
	maxReportedGSMCells,
	maxSRBsetup,
	maxRL,
	maxRL-1,
	maxSCCPCH,
	maxSat,
	maxSIB,
	maxSIB-FACH,
	maxSystemCapability,
	maxTF,
	maxTF-CPCH,
	maxTFC,
	maxTFCI-2-Combs,
	maxTGPS,
	maxTrCH,
	maxTrCHpreconf,
	maxTS,
	maxTS-1,
	maxURA
FROM Constant-definitions;

Ansi-41-IDNNS ::=							BIT STRING (SIZE (14))

CN-DomainIdentity ::=				ENUMERATED {
										cs-domain,
										ps-domain }

CN-DomainInformation ::=			SEQUENCE {
	cn-DomainIdentity					CN-DomainIdentity,
	cn-DomainSpecificNAS-Info			NAS-SystemInformationGSM-MAP
}

CN-DomainInformationFull ::=		SEQUENCE {
	cn-DomainIdentity					CN-DomainIdentity,
	cn-DomainSpecificNAS-Info			NAS-SystemInformationGSM-MAP,
	cn-DRX-CycleLengthCoeff				CN-DRX-CycleLengthCoefficient
}

CN-DomainInformationList ::=		SEQUENCE (SIZE (1..maxCNdomains)) OF
										CN-DomainInformation

CN-DomainInformationListFull ::=	SEQUENCE (SIZE (1..maxCNdomains)) OF
										CN-DomainInformationFull

CN-DomainSysInfo ::=				SEQUENCE {
	cn-DomainIdentity					CN-DomainIdentity,
	cn-Type								CHOICE {
		gsm-MAP								NAS-SystemInformationGSM-MAP,
		ansi-41								NAS-SystemInformationANSI-41
	},
	cn-DRX-CycleLengthCoeff				CN-DRX-CycleLengthCoefficient
}

CN-DomainSysInfoList ::=			SEQUENCE (SIZE (1..maxCNdomains)) OF
										CN-DomainSysInfo

CN-InformationInfo ::=				SEQUENCE {
	plmn-Identity						PLMN-Identity						OPTIONAL,
	cn-CommonGSM-MAP-NAS-SysInfo		NAS-SystemInformationGSM-MAP		OPTIONAL,
	cn-DomainInformationList			CN-DomainInformationList			OPTIONAL
}

CN-InformationInfoFull ::=			SEQUENCE {
	plmn-Identity						PLMN-Identity						OPTIONAL,
	cn-CommonGSM-MAP-NAS-SysInfo		NAS-SystemInformationGSM-MAP		OPTIONAL,
	cn-DomainInformationListFull		CN-DomainInformationListFull		OPTIONAL
}

Digit ::=							INTEGER (0..9)

Gsm-map-IDNNS ::=							SEQUENCE {
	routingbasis									CHOICE {
		localPTMSI										SEQUENCE {
			routingparameter								RoutingParameter
		},
		tMSIofsamePLMN									SEQUENCE {
			routingparameter								RoutingParameter
		},
		tMSIofdifferentPLMN							SEQUENCE {
			routingparameter								RoutingParameter
		},
		iMSIresponsetopaging							SEQUENCE {
			routingparameter								RoutingParameter
		},
		iMSIcauseUEinitiatedEvent						SEQUENCE {
			routingparameter								RoutingParameter
		},
		iMEI											SEQUENCE {
			routingparameter								RoutingParameter
		},
		spare2											SEQUENCE {
			routingparameter								RoutingParameter
		},
		spare1											SEQUENCE {
			routingparameter								RoutingParameter
		}
	},
	enteredparameter									BOOLEAN
}

IMEI ::=							SEQUENCE (SIZE (15)) OF
										IMEI-Digit

IMEI-Digit ::=						INTEGER (0..15)

IMSI-GSM-MAP ::=					SEQUENCE (SIZE (6..21)) OF
										Digit

IntraDomainNasNodeSelector ::=					SEQUENCE {
	version											CHOICE {
		release99										SEQUENCE {
			cn-Type											CHOICE {
				gsm-Map-IDNNS									Gsm-map-IDNNS,
				ansi-41-IDNNS									Ansi-41-IDNNS
			}
		},
		later											SEQUENCE {
			futurecoding									BIT STRING (SIZE (15))
		}
	}
}

LAI ::=								SEQUENCE {
	plmn-Identity						PLMN-Identity,
	lac									BIT STRING (SIZE (16))
}

MCC ::=								SEQUENCE (SIZE (3)) OF
										Digit

MNC ::=								SEQUENCE (SIZE (2..3)) OF
										Digit

NAS-Message ::=						OCTET STRING (SIZE (1..4095))

NAS-Synchronisation-Indicator	::=		BIT STRING(SIZE(4))

NAS-SystemInformationGSM-MAP ::=	OCTET STRING (SIZE (1..8))

P-TMSI-GSM-MAP ::=					BIT STRING (SIZE (32))

PagingRecordTypeID ::=				ENUMERATED {
										imsi-GSM-MAP,
										tmsi-GSM-MAP-P-TMSI,
										imsi-DS-41,
										tmsi-DS-41 }

PLMN-Identity ::=					SEQUENCE {
	mcc									MCC,
	mnc									MNC
}

PLMN-Type ::=						CHOICE {
	gsm-MAP								SEQUENCE {
		plmn-Identity						PLMN-Identity
	},
	ansi-41							SEQUENCE {
		p-REV							P-REV,
		min-P-REV						Min-P-REV,
		sid								SID,
		nid								NID
	},
	gsm-MAP-and-ANSI-41				SEQUENCE {
		plmn-Identity					PLMN-Identity,
		p-REV							P-REV,
		min-P-REV						Min-P-REV,
		sid								SID,
		nid								NID
	},
	spare								NULL
}

RAB-Identity ::=					CHOICE {
	gsm-MAP-RAB-Identity				BIT STRING (SIZE (8)),
	ansi-41-RAB-Identity				BIT STRING (SIZE (8))
}

RAI ::=								SEQUENCE {
	lai									LAI,
	rac									RoutingAreaCode
}

RoutingAreaCode ::=					BIT STRING (SIZE (8))

RoutingParameter ::=							BIT STRING (SIZE (10))

TMSI-GSM-MAP ::=					BIT STRING (SIZE (32))

-- ***************************************************
--
--     UTRAN MOBILITY INFORMATION ELEMENTS (10.3.2)
--
-- ***************************************************

AccessClassBarred ::=				ENUMERATED {
										barred, notBarred }

AccessClassBarredList ::=			SEQUENCE (SIZE (maxAC)) OF
										AccessClassBarred

AllowedIndicator ::=				ENUMERATED {
										allowed, notAllowed }

CellAccessRestriction ::=			SEQUENCE {
	cellBarred							CellBarred,
	cellReservedForOperatorUse			ReservedIndicator,
	cellReservationExtension			ReservedIndicator,
	-- NOTE: IE accessClassBarredList should not be included if the IE CellAccessRestriction
	-- is included in the IE SysInfoType4
	accessClassBarredList				AccessClassBarredList				OPTIONAL
}

CellBarred ::=						CHOICE {
	barred								SEQUENCE {
		intraFreqCellReselectionInd			AllowedIndicator,
		t-Barred							T-Barred
	},
	notBarred							NULL
}

CellIdentity ::=					BIT STRING (SIZE (28))

CellSelectReselectInfoSIB-3-4 ::=	SEQUENCE {
	mappingInfo							MappingInfo							OPTIONAL,
	cellSelectQualityMeasure			CHOICE {
		cpich-Ec-N0							SEQUENCE {
			-- Default value for q-HYST-2-S is q-HYST-1-S
			q-HYST-2-S							Q-Hyst-S					OPTIONAL
		},
		cpich-RSCP							NULL
	},
	modeSpecificInfo					CHOICE {
		fdd									SEQUENCE {
			s-Intrasearch						S-SearchQual				OPTIONAL,
			s-Intersearch						S-SearchQual				OPTIONAL,
			s-SearchHCS							S-SearchRXLEV				OPTIONAL,
			rat-List							RAT-FDD-InfoList			OPTIONAL,
			q-QualMin							Q-QualMin,
			q-RxlevMin							Q-RxlevMin
		},
		tdd									SEQUENCE {
			s-Intrasearch						S-SearchRXLEV				OPTIONAL,
			s-Intersearch						S-SearchRXLEV				OPTIONAL,
			s-SearchHCS							S-SearchRXLEV				OPTIONAL,
			rat-List							RAT-TDD-InfoList			OPTIONAL,
			q-RxlevMin							Q-RxlevMin
		}
	},	
	q-Hyst-l-S							Q-Hyst-S,
	t-Reselection-S						T-Reselection-S,
	hcs-ServingCellInformation			HCS-ServingCellInformation			OPTIONAL,
	maxAllowedUL-TX-Power				MaxAllowedUL-TX-Power
}

MapParameter ::=					INTEGER (0..99)

Mapping ::=							SEQUENCE {
	rat									RAT,
	mappingFunctionParameterList		MappingFunctionParameterList
}

MappingFunctionParameter ::=		SEQUENCE {
	functionType						MappingFunctionType,
	mapParameter1						MapParameter						OPTIONAL,
	mapParameter2						MapParameter,
	-- the presence of upperLimit is conditional on the number of repetition
	upperLimit							UpperLimit							OPTIONAL
}

MappingFunctionParameterList ::=	SEQUENCE (SIZE (1..maxMeasIntervals)) OF
										MappingFunctionParameter

MappingFunctionType ::=				ENUMERATED {
										linear,
										functionType2,
										functionType3,
										functionType4 }

MappingInfo ::=						SEQUENCE (SIZE (1..maxRAT)) OF
										Mapping

-- Actual value Q-Hyst-S = IE value * 2
Q-Hyst-S ::=						INTEGER (0..20)

RAT ::=								ENUMERATED {
										utra-FDD,
										utra-TDD,
										gsm,
										cdma2000 }

RAT-FDD-Info ::=					SEQUENCE {
	rat-Identifier						RAT-Identifier,
	s-SearchRAT							S-SearchQual,
	s-HCS-RAT							S-SearchRXLEV							OPTIONAL,
	s-Limit-SearchRAT					S-SearchQual
}

RAT-FDD-InfoList ::=				SEQUENCE (SIZE (1..maxOtherRAT)) OF
										RAT-FDD-Info

RAT-Identifier ::=					ENUMERATED {
										gsm, cdma2000 }

RAT-TDD-Info ::=					SEQUENCE {
	rat-Identifier						RAT-Identifier,
	s-SearchRAT							S-SearchRXLEV,
	s-HCS-RAT							S-SearchRXLEV						OPTIONAL,
	s-Limit-SearchRAT					S-SearchRXLEV
}

RAT-TDD-InfoList ::=				SEQUENCE (SIZE (1..maxOtherRAT)) OF
										RAT-TDD-Info

ReservedIndicator ::=				ENUMERATED {
										reserved,
										notReserved }

-- Actual value S-SearchQual = IE value * 2
S-SearchQual ::=						INTEGER (-16..10)

-- Actual value S-SearchRXLEV = (IE value * 2) + 1
S-SearchRXLEV ::=						INTEGER (-53..45)

T-Barred ::=						ENUMERATED {
										s10, s20, s40, s80,
										s160, s320, s640, s1280 }

T-Reselection-S ::=					INTEGER (0..31)

-- For UpperLimit the used range depends on the RAT used.
UpperLimit ::=						INTEGER (1..91)

URA-Identity ::=					BIT STRING (SIZE (16))

URA-IdentityList ::=				SEQUENCE (SIZE (1..maxURA)) OF
										URA-Identity

-- ***************************************************
--
--     USER EQUIPMENT INFORMATION ELEMENTS (10.3.3)
--
-- ***************************************************

-- TABULAR : for ActivationTime, value 'now' always appears as default, and is encoded
-- by absence of the field
ActivationTime ::=					INTEGER (0..255)

BackoffControlParams ::=			SEQUENCE {
	n-AP-RetransMax						N-AP-RetransMax,
	n-AccessFails						N-AccessFails,
	nf-BO-NoAICH						NF-BO-NoAICH,
	ns-BO-Busy							NS-BO-Busy,
	nf-BO-AllBusy						NF-BO-AllBusy,
	nf-BO-Mismatch						NF-BO-Mismatch,
	t-CPCH								T-CPCH
}

C-RNTI ::=							BIT STRING (SIZE (16))

CapabilityUpdateRequirement ::=		SEQUENCE {
	ue-RadioCapabilityFDDUpdateRequirement	BOOLEAN,
	ue-RadioCapabilityTDDUpdateRequirement	BOOLEAN,
	systemSpecificCapUpdateReqList		SystemSpecificCapUpdateReqList		OPTIONAL
}

CellUpdateCause ::=					ENUMERATED {
										cellReselection,
										periodicalCellUpdate,
										uplinkDataTransmission,
										utran-pagingResponse,
										re-enteredServiceArea,
										radiolinkFailure,
										rlc-unrecoverableError,
										spare1 }

ChipRateCapability ::=				ENUMERATED {
										mcps3-84, mcps1-28 }

CipheringAlgorithm ::=				ENUMERATED {
										uea0, uea1 }

CipheringModeCommand ::=			CHOICE {
	startRestart						CipheringAlgorithm,
	dummy						NULL
}

CipheringModeInfo ::=				SEQUENCE {
	-- TABULAR: The ciphering algorithm is included in the CipheringModeCommand.
	cipheringModeCommand				CipheringModeCommand,
	activationTimeForDPCH				ActivationTime						OPTIONAL,
	rb-DL-CiphActivationTimeInfo		RB-ActivationTimeInfoList			OPTIONAL
}

CN-DRX-CycleLengthCoefficient ::=	INTEGER (6..9)

CN-PagedUE-Identity ::=				CHOICE {
	imsi-GSM-MAP						IMSI-GSM-MAP,
	tmsi-GSM-MAP						TMSI-GSM-MAP,
	p-TMSI-GSM-MAP						P-TMSI-GSM-MAP,
	imsi-DS-41							IMSI-DS-41,
	tmsi-DS-41							TMSI-DS-41,
	spare3								NULL,
	spare2								NULL,
	spare1								NULL
}

CompressedModeMeasCapability ::=	SEQUENCE {
	fdd-Measurements					BOOLEAN,
	-- TABULAR: The IEs tdd-Measurements, gsm-Measurements and multiCarrierMeasurements
	-- are made optional since they are conditional based on another information element.
	-- Their absence corresponds to the case where the condition is not true.
	tdd-Measurements					BOOLEAN								OPTIONAL,
	gsm-Measurements					GSM-Measurements					OPTIONAL,
	multiCarrierMeasurements			BOOLEAN								OPTIONAL
}

CompressedModeMeasCapabFDDList ::=	SEQUENCE (SIZE (1..maxFreqBandsFDD)) OF
										CompressedModeMeasCapabFDD

CompressedModeMeasCapabFDD ::=		SEQUENCE {
	radioFrequencyBandFDD				RadioFrequencyBandFDD	OPTIONAL,
	dl-MeasurementsFDD					BOOLEAN,
	ul-MeasurementsFDD					BOOLEAN
}

CompressedModeMeasCapabTDDList ::=	SEQUENCE (SIZE (1..maxFreqBandsTDD)) OF
										CompressedModeMeasCapabTDD

CompressedModeMeasCapabTDD ::=		SEQUENCE {
	radioFrequencyBandTDD				RadioFrequencyBandTDD,
	dl-MeasurementsTDD					BOOLEAN,
	ul-MeasurementsTDD					BOOLEAN
}

CompressedModeMeasCapabGSMList ::=	SEQUENCE (SIZE (1..maxFreqBandsGSM)) OF
										CompressedModeMeasCapabGSM

CompressedModeMeasCapabGSM ::=		SEQUENCE {
	radioFrequencyBandGSM				RadioFrequencyBandGSM,
	dl-MeasurementsGSM					BOOLEAN,
	ul-MeasurementsGSM					BOOLEAN
}

CompressedModeMeasCapabMC ::=		SEQUENCE {
	dl-MeasurementsMC					BOOLEAN,
	ul-MeasurementsMC					BOOLEAN
}

CPCH-Parameters ::=					SEQUENCE {
	initialPriorityDelayList			InitialPriorityDelayList			OPTIONAL,
	backoffControlParams				BackoffControlParams,
	-- TABULAR: TPC step size nested inside PowerControlAlgorithm
	powerControlAlgorithm				PowerControlAlgorithm,
	dl-DPCCH-BER						DL-DPCCH-BER
}

DL-DPCCH-BER ::=					INTEGER (0..63)

DL-PhysChCapabilityFDD ::=			SEQUENCE {
	maxNoDPCH-PDSCH-Codes				INTEGER (1..8),
	maxNoPhysChBitsReceived				MaxNoPhysChBitsReceived,
	supportForSF-512					BOOLEAN,
	supportOfPDSCH						BOOLEAN,
	simultaneousSCCPCH-DPCH-Reception	SimultaneousSCCPCH-DPCH-Reception
}

DL-PhysChCapabilityFDD-v380ext ::=			SEQUENCE {
	supportOfDedicatedPilotsForChEstimation		SupportOfDedicatedPilotsForChEstimation		OPTIONAL
}

SupportOfDedicatedPilotsForChEstimation ::=			ENUMERATED { true }

DL-PhysChCapabilityTDD ::=			SEQUENCE {
	maxTS-PerFrame						MaxTS-PerFrame,
	maxPhysChPerFrame					MaxPhysChPerFrame,
	minimumSF							MinimumSF-DL,
	supportOfPDSCH						BOOLEAN,
	maxPhysChPerTS						MaxPhysChPerTS	
}

DL-TransChCapability ::=			SEQUENCE {
	maxNoBitsReceived					MaxNoBits,
	maxConvCodeBitsReceived				MaxNoBits,
	turboDecodingSupport				TurboSupport,
	maxSimultaneousTransChs				MaxSimultaneousTransChsDL,
	maxSimultaneousCCTrCH-Count			MaxSimultaneousCCTrCH-Count,
	maxReceivedTransportBlocks			MaxTransportBlocksDL,
	maxNumberOfTFC						MaxNumberOfTFC-DL,
	maxNumberOfTF						MaxNumberOfTF
}

DRAC-SysInfo ::=					SEQUENCE {
	transmissionProbability				TransmissionProbability,
	maximumBitRate						MaximumBitRate
}

DRAC-SysInfoList ::=				SEQUENCE (SIZE (1..maxDRACclasses)) OF
										DRAC-SysInfo

DSCH-RNTI ::=						BIT STRING (SIZE (16))

ESN-DS-41 ::=						BIT STRING (SIZE (32))

EstablishmentCause ::=				ENUMERATED {
										originatingConversationalCall,
										originatingStreamingCall,
										originatingInteractiveCall,
										originatingBackgroundCall,
										originatingSubscribedTrafficCall,
										terminatingConversationalCall,
										terminatingStreamingCall,
										terminatingInteractiveCall,
										terminatingBackgroundCall,
										emergencyCall,
										interRAT-CellReselection,
										interRAT-CellChangeOrder,
										registration,
										detach,
										originatingHighPrioritySignalling,
										originatingLowPrioritySignalling,
										callRe-establishment,
										terminatingHighPrioritySignalling,
										terminatingLowPrioritySignalling,
										terminatingCauseUnknown,
										spare12,
										spare11,
										spare10,
										spare9,
										spare8,
										spare7,
										spare6,
										spare5,
										spare4,
										spare3,
										spare2,
										spare1 }

FailureCauseWithProtErr ::=			CHOICE {
	configurationUnsupported			NULL,
	physicalChannelFailure				NULL,
	incompatibleSimultaneousReconfiguration
										NULL,
	compressedModeRuntimeError			TGPSI,
	protocolError						ProtocolErrorInformation,
	cellUpdateOccurred					NULL,
	invalidConfiguration				NULL,
	configurationIncomplete				NULL,
	unsupportedMeasurement				NULL,
	spare7								NULL,
	spare6								NULL,
	spare5								NULL,
	spare4								NULL,
	spare3								NULL,
	spare2								NULL,
	spare1								NULL
}

FailureCauseWithProtErrTrId ::=		SEQUENCE {
		rrc-TransactionIdentifier		RRC-TransactionIdentifier,
		failureCause					FailureCauseWithProtErr
}

GSM-Measurements ::=				SEQUENCE {
	gsm900								BOOLEAN,
	dcs1800								BOOLEAN,
	gsm1900								BOOLEAN
}


AccessStratumReleaseIndicator ::=	ENUMERATED {
										r99 }

UESpecificBehaviourInformation1idle ::= BIT STRING (SIZE (4))

UESpecificBehaviourInformation1interRAT ::= BIT STRING (SIZE (8))

IMSI-and-ESN-DS-41 ::=				SEQUENCE {
	imsi-DS-41							IMSI-DS-41,
	esn-DS-41							ESN-DS-41
}

IMSI-DS-41 ::=						OCTET STRING (SIZE (5..7))

InitialPriorityDelayList ::=		SEQUENCE (SIZE (1..maxASC)) OF
										NS-IP

InitialUE-Identity ::=				CHOICE {
	imsi								IMSI-GSM-MAP,
	tmsi-and-LAI						TMSI-and-LAI-GSM-MAP,
	p-TMSI-and-RAI						P-TMSI-and-RAI-GSM-MAP,
	imei								IMEI,
	esn-DS-41							ESN-DS-41,
	imsi-DS-41							IMSI-DS-41,
	imsi-and-ESN-DS-41					IMSI-and-ESN-DS-41,
	tmsi-DS-41							TMSI-DS-41
}

IntegrityCheckInfo ::=				SEQUENCE {
	messageAuthenticationCode			MessageAuthenticationCode,
	rrc-MessageSequenceNumber			RRC-MessageSequenceNumber
}

IntegrityProtActivationInfo ::=		SEQUENCE {
	rrc-MessageSequenceNumberList		RRC-MessageSequenceNumberList
}

IntegrityProtectionAlgorithm ::=	ENUMERATED {
										uia1 }


IntegrityProtectionModeCommand ::=	CHOICE {
	startIntegrityProtection			SEQUENCE {
		integrityProtInitNumber				IntegrityProtInitNumber
	},
	modify								SEQUENCE {
		dl-IntegrityProtActivationInfo		IntegrityProtActivationInfo
	}
}

IntegrityProtectionModeInfo ::=		SEQUENCE {
	-- TABULAR: DL integrity protection activation info and Integrity
	-- protection intialisation number have been nested inside
	-- IntegrityProtectionModeCommand.
	integrityProtectionModeCommand		IntegrityProtectionModeCommand,
	integrityProtectionAlgorithm		IntegrityProtectionAlgorithm		OPTIONAL	
}

IntegrityProtInitNumber ::=			BIT STRING (SIZE (32))

MaxHcContextSpace ::=					ENUMERATED	{
											by512, by1024, by2048, by4096,
											by8192 }


MaximumAM-EntityNumberRLC-Cap ::=	ENUMERATED {
										am3, am4, am5, am6,
										am8, am16, am30 }

-- Actual value MaximumBitRate = IE value * 16
MaximumBitRate ::=					INTEGER (0..32)

MaximumRLC-WindowSize ::=			ENUMERATED { mws2047, mws4095 }

MaxNoDPDCH-BitsTransmitted ::=		ENUMERATED {
										b600, b1200, b2400, b4800,
										b9600, b19200, b28800, b38400,
										b48000, b57600 }

MaxNoBits ::=						ENUMERATED {
										b640, b1280, b2560, b3840, b5120,
										b6400, b7680, b8960, b10240,
										b20480, b40960, b81920, b163840 }

MaxNoPhysChBitsReceived ::=			ENUMERATED {
										b600, b1200, b2400, b3600,
										b4800, b7200, b9600, b14400,
										b19200, b28800, b38400, b48000,
										b57600, b67200, b76800 }

MaxNoSCCPCH-RL ::=					ENUMERATED {
										rl1 }

MaxNumberOfTF ::=					ENUMERATED {
										tf32, tf64, tf128, tf256,
										tf512, tf1024 }

MaxNumberOfTFC-DL ::=				ENUMERATED {
										tfc16, tfc32, tfc48, tfc64, tfc96,
										tfc128, tfc256, tfc512, tfc1024 }

MaxNumberOfTFC-UL ::=				ENUMERATED {
										tfc4, tfc8, tfc16, tfc32, tfc48, tfc64,
										tfc96, tfc128, tfc256, tfc512, tfc1024 }

MaxPhysChPerFrame ::=				INTEGER (1..224)

MaxPhysChPerTimeslot ::=			ENUMERATED {
										ts1, ts2 }

MaxPhysChPerTS ::=					INTEGER (1..16)

MaxSimultaneousCCTrCH-Count ::=		INTEGER (1..8)

MaxSimultaneousTransChsDL ::=		ENUMERATED {
										e4, e8, e16, e32 }

MaxSimultaneousTransChsUL ::=		ENUMERATED {
										e2, e4, e8, e16, e32 }

MaxTransportBlocksDL ::=			ENUMERATED {
										tb4, tb8, tb16, tb32, tb48,
										tb64, tb96, tb128, tb256, tb512 }

MaxTransportBlocksUL ::=			ENUMERATED {
										tb2, tb4, tb8, tb16, tb32, tb48,
										tb64, tb96, tb128, tb256, tb512 }

MaxTS-PerFrame ::=					INTEGER (1..14)

-- TABULAR: MeasurementCapability contains dependencies to UE-MultiModeRAT-Capability,
-- the conditional fields have been left mandatory for now.
MeasurementCapability ::=			SEQUENCE {
	downlinkCompressedMode				CompressedModeMeasCapability,
	uplinkCompressedMode				CompressedModeMeasCapability	
}

MeasurementCapabilityExt ::=		SEQUENCE{
	compressedModeMeasCapabFDDList		CompressedModeMeasCapabFDDList,
	compressedModeMeasCapabTDDList		CompressedModeMeasCapabTDDList	OPTIONAL,
	compressedModeMeasCapabGSMList		CompressedModeMeasCapabGSMList	OPTIONAL,
	compressedModeMeasCapabMC			CompressedModeMeasCapabMC		OPTIONAL
}

MessageAuthenticationCode ::=		BIT STRING (SIZE (32))

MinimumSF-DL ::=					ENUMERATED {
										sf1, sf16 }

MinimumSF-UL ::=					ENUMERATED {
										sf1, sf2, sf4, sf8, sf16 }

MultiModeCapability ::=				ENUMERATED {
										tdd, fdd, fdd-tdd }

MultiRAT-Capability ::=				SEQUENCE {
	supportOfGSM						BOOLEAN,
	supportOfMulticarrier				BOOLEAN
}

N-300 ::=							INTEGER (0..7)

N-301 ::=							INTEGER (0..7)

N-302 ::=							INTEGER (0..7)

N-304 ::=							INTEGER (0..7)

N-308 ::=							INTEGER (1..8)

N-310 ::=							INTEGER (0..7)

N-312 ::=							ENUMERATED {
										s1, s50, s100, s200, s400,
										s600, s800, s1000 }

N-312ext ::=						ENUMERATED {
										s2, s4, s10, s20 }

N-313 ::=							ENUMERATED {
										s1, s2, s4, s10, s20,
										s50, s100, s200 }

N-315 ::=							ENUMERATED {
										s1, s50, s100, s200, s400,
										s600, s800, s1000 }

N-315ext ::=						ENUMERATED  {
										s2, s4, s10, s20 }

N-AccessFails ::=					INTEGER (1..64)

N-AP-RetransMax ::=					INTEGER (1..64)

NetworkAssistedGPS-Supported ::=	ENUMERATED {
										networkBased,
										ue-Based,
										bothNetworkAndUE-Based,
										noNetworkAssistedGPS }

NF-BO-AllBusy ::=					INTEGER (0..31)

NF-BO-NoAICH ::=					INTEGER (0..31)

NF-BO-Mismatch ::=					INTEGER (0..127)

NS-BO-Busy ::=						INTEGER (0..63)

NS-IP ::=							INTEGER (0..28)

P-TMSI-and-RAI-GSM-MAP ::=			SEQUENCE {
	p-TMSI								P-TMSI-GSM-MAP,
	rai									RAI
}

PagingCause ::=						ENUMERATED {
										terminatingConversationalCall,
										terminatingStreamingCall,
										terminatingInteractiveCall,
										terminatingBackgroundCall,
										terminatingHighPrioritySignalling,
										terminatingLowPrioritySignalling,
										terminatingCauseUnknown,
										spare
 }

PagingRecord ::=					CHOICE {
	cn-Identity							SEQUENCE {
		pagingCause							PagingCause,
		cn-DomainIdentity					CN-DomainIdentity,
		cn-pagedUE-Identity					CN-PagedUE-Identity
	},
	utran-Identity						SEQUENCE {
		u-RNTI								U-RNTI,
		cn-OriginatedPage-connectedMode-UE	SEQUENCE {
			pagingCause							PagingCause,
			cn-DomainIdentity					CN-DomainIdentity,
			pagingRecordTypeID					PagingRecordTypeID
		}																	OPTIONAL
	}
}

PagingRecordList ::=				SEQUENCE (SIZE (1..maxPage1)) OF
										PagingRecord

PDCP-Capability ::=					SEQUENCE {
	losslessSRNS-RelocationSupport		BOOLEAN,
	supportForRfc2507					CHOICE {
		notSupported						NULL,
		supported							MaxHcContextSpace
	}
}

PhysicalChannelCapability ::=		SEQUENCE {
		fddPhysChCapability					SEQUENCE {
			downlinkPhysChCapability			DL-PhysChCapabilityFDD,
			uplinkPhysChCapability				UL-PhysChCapabilityFDD
		}											OPTIONAL,
		tddPhysChCapability					SEQUENCE {
			downlinkPhysChCapability			DL-PhysChCapabilityTDD,
			uplinkPhysChCapability				UL-PhysChCapabilityTDD
		}											OPTIONAL
}

ProtocolErrorCause ::=				ENUMERATED {
										asn1-ViolationOrEncodingError,
										messageTypeNonexistent,
										messageNotCompatibleWithReceiverState,
										ie-ValueNotComprehended,
										informationElementMissing,
										messageExtensionNotComprehended,
										spare2, spare1 }

ProtocolErrorIndicator ::=			ENUMERATED {
										noError, errorOccurred }

ProtocolErrorIndicatorWithMoreInfo ::=
									CHOICE {
	noError								NULL,
	errorOccurred						SEQUENCE {		
		rrc-TransactionIdentifier			RRC-TransactionIdentifier,
		protocolErrorInformation			ProtocolErrorInformation
	}
}

ProtocolErrorMoreInformation ::=	SEQUENCE {
	diagnosticsType						CHOICE {
		type1								CHOICE {
			asn1-ViolationOrEncodingError		NULL,
			messageTypeNonexistent				NULL,
			messageNotCompatibleWithReceiverState
												IdentificationOfReceivedMessage,
			ie-ValueNotComprehended				IdentificationOfReceivedMessage,
			conditionalInformationElementError	IdentificationOfReceivedMessage,
			messageExtensionNotComprehended		IdentificationOfReceivedMessage,
			spare1								NULL,
			spare2								NULL
		},
		spare								NULL
	}
}

RadioFrequencyBandFDD ::=			ENUMERATED {
										fdd2100,
										fdd1900,
										spare6, spare5, spare4, spare3, spare2, spare1}

RadioFrequencyBandTDDList ::=		ENUMERATED {
										a, b, c, ab, ac, bc, abc, spare }

RadioFrequencyBandTDD ::=			ENUMERATED {a, b, c, spare}

RadioFrequencyBandGSM ::=			ENUMERATED {
										gsm450,
										gsm480,
										gsm850,
										gsm900P,
										gsm900E,
										gsm1800,
										gsm1900,
										spare9, spare8, spare7, spare6, spare5,
										spare4, spare3, spare2, spare1}

Rb-timer-indicator ::=				SEQUENCE {
	t314-expired						BOOLEAN,
	t315-expired						BOOLEAN }

Re-EstablishmentTimer ::=			ENUMERATED {
										useT314, useT315
}

RedirectionInfo ::=					CHOICE {
	frequencyInfo						FrequencyInfo,
	interRATInfo						InterRATInfo
}

RejectionCause ::=					ENUMERATED {
										congestion,
										unspecified }

ReleaseCause ::=					ENUMERATED {
										normalEvent,
										unspecified,
										pre-emptiveRelease,
										congestion,
										re-establishmentReject,
										directedsignallingconnectionre-establishment,
										userInactivity,
										spare }

RF-Capability ::=					SEQUENCE {
		fddRF-Capability				SEQUENCE {
			ue-PowerClass					UE-PowerClass,
			txRxFrequencySeparation			TxRxFrequencySeparation
		}									OPTIONAL,
		tddRF-Capability							SEQUENCE {
			ue-PowerClass				UE-PowerClass,
			radioFrequencyTDDBandList	RadioFrequencyBandTDDList,
			chipRateCapability			ChipRateCapability
		}									OPTIONAL

}

RLC-Capability ::=					SEQUENCE {
	totalRLC-AM-BufferSize				TotalRLC-AM-BufferSize,
	maximumRLC-WindowSize				MaximumRLC-WindowSize,
	maximumAM-EntityNumber				MaximumAM-EntityNumberRLC-Cap
}

RRC-MessageSequenceNumber ::=		INTEGER (0..15)


RRC-MessageSequenceNumberList ::=	SEQUENCE (SIZE (4..5)) OF
										RRC-MessageSequenceNumber

RRC-StateIndicator ::=				ENUMERATED {
										cell-DCH, cell-FACH, cell-PCH, ura-PCH }

RRC-TransactionIdentifier ::=		INTEGER (0..3)

S-RNTI ::=							BIT STRING (SIZE (20))

S-RNTI-2 ::=						BIT STRING (SIZE (10))

SecurityCapability ::=				SEQUENCE {
	cipheringAlgorithmCap				BIT STRING {
										-- For each bit value "0" means false/ not supported
											spare15(0),
											spare14(1),
											spare13(2),
											spare12(3),
											spare11(4),
											spare10(5),
											spare9(6),
											spare8(7),
											spare7(8),
											spare6(9),
											spare5(10),
											spare4(11),
											spare3(12),
											spare2(13),
											uea1(14),
											uea0(15)
											}	(SIZE (16)),
	integrityProtectionAlgorithmCap		BIT STRING {
										-- For each bit value "0" means false/ not supported
											spare15(0),
											spare14(1),
											spare13(2),
											spare12(3),
											spare11(4),
											spare10(5),
											spare9(6),
											spare8(7),
											spare7(8),
											spare6(9),
											spare5(10),
											spare4(11),
											spare3(12),
											spare2(13),
											uia1(14),
											spare0(15)
											}	(SIZE (16))
}

SimultaneousSCCPCH-DPCH-Reception ::= CHOICE {
	notSupported						NULL,
	supported							SEQUENCE {
		maxNoSCCPCH-RL						MaxNoSCCPCH-RL,
		-- simultaneousSCCPCH-DPCH-DPDCH-Reception is applicable only if
		-- the IE Support of PDSCH = TRUE
		simultaneousSCCPCH-DPCH-DPDCH-Reception
											BOOLEAN
	}
}

SRNC-Identity ::=					BIT STRING (SIZE (12))


START-Value ::=						BIT STRING (SIZE (20))

STARTList ::=						SEQUENCE (SIZE (1..maxCNdomains)) OF
										STARTSingle

STARTSingle ::=						SEQUENCE {
	cn-DomainIdentity					CN-DomainIdentity,
	start-Value							START-Value			
}

SystemSpecificCapUpdateReq ::=		ENUMERATED {
										gsm }

SystemSpecificCapUpdateReqList ::= SEQUENCE (SIZE (1..maxSystemCapability)) OF
										SystemSpecificCapUpdateReq


T-300 ::=							ENUMERATED {
										ms100, ms200, ms400, ms600, ms800,
										ms1000, ms1200, ms1400, ms1600,
										ms1800, ms2000, ms3000, ms4000,
										ms6000, ms8000 }

T-301 ::=							ENUMERATED {
										ms100, ms200, ms400, ms600, ms800,
										ms1000, ms1200, ms1400, ms1600,
										ms1800, ms2000, ms3000, ms4000,
										ms6000, ms8000, spare }

T-302 ::=							ENUMERATED {
										ms100, ms200, ms400, ms600, ms800,
										ms1000, ms1200, ms1400, ms1600,
										ms1800, ms2000, ms3000, ms4000,
										ms6000, ms8000, spare }

T-304 ::=							ENUMERATED {
										ms100, ms200, ms400,
										ms1000, ms2000, spare3, spare2, spare1 }

T-305 ::=							ENUMERATED {
										noUpdate, m5, m10, m30,
										m60, m120, m360, m720 }

T-307 ::=							ENUMERATED {
										s5, s10, s15, s20,
										s30, s40, s50, spare }

T-308 ::=							ENUMERATED {
										ms40, ms80, ms160, ms320 }

T-309 ::=							INTEGER (1..8)

T-310 ::=							ENUMERATED {
										ms40, ms80, ms120, ms160,
										ms200, ms240, ms280, ms320 }

T-311 ::=							ENUMERATED {
										ms250, ms500, ms750, ms1000,
										ms1250, ms1500, ms1750, ms2000 }

-- The value 0 for T-312 is not used in this version of the specification
T-312 ::=							INTEGER (0..15)

T-313 ::=							INTEGER (0..15)

T-314 ::=							ENUMERATED {
										s0, s2, s4, s6, s8,
										s12, s16, s20 }

T-315 ::=							ENUMERATED {
										s0, s10, s30, s60, s180,
										s600, s1200, s1800 }

T-316 ::=							ENUMERATED {
										s0, s10, s20, s30, s40,
										s50, s-inf, spare }

-- All the values should be interpreted as "infinity"
T-317 ::=							ENUMERATED {
										s0, s10, s30, s60, s180,
										s600, s1200, s1800 }

T-CPCH ::=							ENUMERATED {
										ct0, ct1 }

TMSI-and-LAI-GSM-MAP ::=			SEQUENCE {
	tmsi								TMSI-GSM-MAP,
	lai									LAI
}

TMSI-DS-41 ::=						OCTET STRING (SIZE (2..17))

TotalRLC-AM-BufferSize ::=			ENUMERATED {
										kb2, kb10, kb50, kb100,
										kb150, kb500, kb1000, spare }

-- Actual value TransmissionProbability = IE value * 0.125
TransmissionProbability ::=			INTEGER (1..8)

TransportChannelCapability ::=		SEQUENCE {
	dl-TransChCapability				DL-TransChCapability,
	ul-TransChCapability				UL-TransChCapability	
}

TurboSupport ::=					CHOICE {
	notSupported						NULL,
	supported							MaxNoBits
}

TxRxFrequencySeparation ::=			ENUMERATED {
										mhz190, mhz174-8-205-2,
										mhz134-8-245-2 }

U-RNTI ::=							SEQUENCE {
	srnc-Identity						SRNC-Identity,
	s-RNTI								S-RNTI
}

U-RNTI-Short ::=					SEQUENCE {
	srnc-Identity						SRNC-Identity,
	s-RNTI-2							S-RNTI-2
}

UE-ConnTimersAndConstants ::=		SEQUENCE {
-- Optional is used also for parameters for which the default value is the last one read in SIB1
-- t-301 and n-301 should not be used by the UE in this version of the specification
	t-301								T-301								DEFAULT ms2000,
	n-301								N-301								DEFAULT 2,
	t-302								T-302								DEFAULT ms4000,
	n-302								N-302								DEFAULT 3,
	t-304								T-304								DEFAULT ms2000,
	n-304								N-304								DEFAULT 2,
	t-305								T-305								DEFAULT m30,
	t-307								T-307								DEFAULT s30,
	t-308								T-308								DEFAULT ms160,
	t-309								T-309								DEFAULT 5,
	t-310								T-310								DEFAULT ms160,
	n-310								N-310								DEFAULT 4,
	t-311								T-311								DEFAULT ms2000,
	t-312								T-312								DEFAULT 1,
	-- n-312 shall be ignored if n-312 in UE-ConnTimersAndConstants-v3a0ext is present, and the
	-- value of that element shall be used instead.
	n-312								N-312								DEFAULT s1,
	t-313								T-313								DEFAULT 3,
	n-313								N-313								DEFAULT s20,
	t-314								T-314								DEFAULT s12,
	t-315								T-315								DEFAULT s180,
	-- n-315 shall be ignored if n-315 in UE-ConnTimersAndConstants-v3a0ext is present, and the
	-- value of that element shall be used instead.
	n-315								N-315								DEFAULT s1,
	t-316								T-316								DEFAULT s30,
	t-317								T-317								DEFAULT s180
}

UE-ConnTimersAndConstants-v3a0ext ::=		SEQUENCE {
	n-312								N-312ext							OPTIONAL,
	n-315								N-315ext							OPTIONAL
}

UE-IdleTimersAndConstants ::=		SEQUENCE {
	t-300								T-300,
	n-300								N-300,
	t-312								T-312,
	-- n-312 shall be ignored if n-312 in UE-IdleTimersAndConstants-v3a0ext is present, and the
	-- value of that element shall be used instead.
	n-312								N-312
}

UE-IdleTimersAndConstants-v3a0ext ::=		SEQUENCE {
	n-312								N-312ext							OPTIONAL
}

UE-MultiModeRAT-Capability ::=		SEQUENCE {
	multiRAT-CapabilityList				MultiRAT-Capability,
	multiModeCapability					MultiModeCapability
}

UE-PowerClass ::=					INTEGER (1..4)

UE-PowerClassExt ::=				ENUMERATED {class1, class2, class3, class4, spare4, spare3, spare2, spare1}

UE-RadioAccessCapability ::=		SEQUENCE {
	accessStratumReleaseIndicator		AccessStratumReleaseIndicator,
	pdcp-Capability						PDCP-Capability,
	rlc-Capability						RLC-Capability,
	transportChannelCapability			TransportChannelCapability,
	rf-Capability						RF-Capability,
	physicalChannelCapability			PhysicalChannelCapability,
	ue-MultiModeRAT-Capability			UE-MultiModeRAT-Capability,
	securityCapability					SecurityCapability,
	ue-positioning-Capability			UE-Positioning-Capability,
	measurementCapability				MeasurementCapability		OPTIONAL
}

UE-RadioAccessCapabilityInfo::=		SEQUENCE {
	ue-RadioAccessCapability			UE-RadioAccessCapability,
	ue-RadioAccessCapability-v370ext	UE-RadioAccessCapability-v370ext
}

UE-RadioAccessCapability-v370ext::=		SEQUENCE {
	ue-RadioAccessCapabBandFDDList		UE-RadioAccessCapabBandFDDList
}

UE-RadioAccessCapability-v380ext::=		SEQUENCE {
	ue-PositioningCapabilityExt-v380	UE-PositioningCapabilityExt-v380
}

UE-RadioAccessCapability-v3a0ext ::=	SEQUENCE {
	ue-PositioningCapabilityExt-v3a0	UE-PositioningCapabilityExt-v3a0
}

UE-PositioningCapabilityExt-v380 ::=	SEQUENCE {
	rx-tx-TimeDifferenceType2Capable	BOOLEAN
}

UE-PositioningCapabilityExt-v3a0 ::=	SEQUENCE {
	validity-CellPCH-UraPCH				ENUMERATED { true }
}

UE-RadioAccessCapabBandFDDList ::=	SEQUENCE (SIZE (1..maxFreqBandsFDD)) OF
											UE-RadioAccessCapabBandFDD

UE-RadioAccessCapabBandFDD ::=		SEQUENCE{
	radioFrequencyBandFDD				RadioFrequencyBandFDD,
	fddRF-Capability					SEQUENCE {
		ue-PowerClass					UE-PowerClassExt,
		txRxFrequencySeparation			TxRxFrequencySeparation
	}																OPTIONAL,
	measurementCapability				MeasurementCapabilityExt
}

UL-PhysChCapabilityFDD ::=			SEQUENCE {
	maxNoDPDCH-BitsTransmitted			MaxNoDPDCH-BitsTransmitted,
	supportOfPCPCH						BOOLEAN	
}

UL-PhysChCapabilityTDD ::=			SEQUENCE {
	maxTS-PerFrame						MaxTS-PerFrame,
	maxPhysChPerTimeslot				MaxPhysChPerTimeslot,
	minimumSF							MinimumSF-UL,
	supportOfPUSCH						BOOLEAN	
}

UL-TransChCapability ::=			SEQUENCE {
	maxNoBitsTransmitted				MaxNoBits,
	maxConvCodeBitsTransmitted			MaxNoBits,
	turboEncodingSupport				TurboSupport,
	maxSimultaneousTransChs				MaxSimultaneousTransChsUL,
	modeSpecificInfo					CHOICE {
		fdd									NULL,
		tdd									SEQUENCE {
			maxSimultaneousCCTrCH-Count			MaxSimultaneousCCTrCH-Count
		}
	},
	maxTransmittedBlocks				MaxTransportBlocksUL,
	maxNumberOfTFC						MaxNumberOfTFC-UL,
	maxNumberOfTF						MaxNumberOfTF
}

UE-Positioning-Capability ::=					SEQUENCE {
	standaloneLocMethodsSupported			BOOLEAN,
	ue-BasedOTDOA-Supported					BOOLEAN,
	networkAssistedGPS-Supported			NetworkAssistedGPS-Supported,
	supportForUE-GPS-TimingOfCellFrames		BOOLEAN,
	supportForIPDL							BOOLEAN
}

UE-SecurityInformation ::=			SEQUENCE {
	start-CS							START-Value
}

URA-UpdateCause ::=					ENUMERATED {
										changeOfURA,
										periodicURAUpdate,
										dummy,
										spare1 }

UTRAN-DRX-CycleLengthCoefficient ::= INTEGER (3..9)

WaitTime ::=						INTEGER (0..15)

-- ***************************************************
--
--     RADIO BEARER INFORMATION ELEMENTS (10.3.4)
--
-- ***************************************************

AlgorithmSpecificInfo ::=			CHOICE {
	rfc2507-Info						RFC2507-Info
}

-- Upper limit of COUNT-C is 2^32 - 1
COUNT-C ::=							INTEGER (0..4294967295)

-- Upper limit of COUNT-C-MSB is 2^25 - 1
COUNT-C-MSB ::=						INTEGER (0..33554431)

DefaultConfigIdentity ::=			INTEGER (0..10)

DefaultConfigMode ::=				ENUMERATED {
										fdd,
										tdd }

DL-AM-RLC-Mode ::=					SEQUENCE {
	inSequenceDelivery					BOOLEAN,
	receivingWindowSize					ReceivingWindowSize,
	dl-RLC-StatusInfo					DL-RLC-StatusInfo
}

DL-CounterSynchronisationInfo ::=		SEQUENCE {
	rB-WithPDCP-InfoList					RB-WithPDCP-InfoList	OPTIONAL
}

DL-LogicalChannelMapping ::=		SEQUENCE {
	-- TABULAR: DL-TransportChannelType contains TransportChannelIdentity as well.
	dl-TransportChannelType				DL-TransportChannelType,
	logicalChannelIdentity				LogicalChannelIdentity				OPTIONAL
}

DL-LogicalChannelMappingList ::=	SEQUENCE (SIZE (1..maxLoCHperRLC)) OF
										DL-LogicalChannelMapping

DL-RLC-Mode ::=						CHOICE {
	dl-AM-RLC-Mode						DL-AM-RLC-Mode,
	dl-UM-RLC-Mode						NULL,
	dl-TM-RLC-Mode						DL-TM-RLC-Mode
}

DL-RLC-StatusInfo ::=				SEQUENCE {
	timerStatusProhibit					TimerStatusProhibit					OPTIONAL,
	timerEPC							TimerEPC							OPTIONAL,
	missingPDU-Indicator					BOOLEAN,
	timerStatusPeriodic					TimerStatusPeriodic					OPTIONAL
}

DL-TM-RLC-Mode ::=					SEQUENCE {
	segmentationIndication					BOOLEAN
}

DL-TransportChannelType ::=			CHOICE {
	dch									TransportChannelIdentity,
	fach								NULL,
	dsch								TransportChannelIdentity,
	dch-and-dsch						TransportChannelIdentityDCHandDSCH
}

ExpectReordering ::=				ENUMERATED {
										reorderingNotExpected,
										reorderingExpected }

ExplicitDiscard ::=					SEQUENCE {
	timerMRW							TimerMRW,
	timerDiscard						TimerDiscard,
	maxMRW								MaxMRW
}

HeaderCompressionInfo ::=			SEQUENCE {
	algorithmSpecificInfo				AlgorithmSpecificInfo
}

HeaderCompressionInfoList ::=		SEQUENCE (SIZE (1..maxPDCPAlgoType)) OF
										HeaderCompressionInfo


LogicalChannelIdentity ::=			INTEGER (1..15)

LosslessSRNS-RelocSupport ::=		CHOICE {
	supported							MaxPDCP-SN-WindowSize,
	notSupported						NULL
}

MAC-LogicalChannelPriority ::=		INTEGER (1..8)

MaxDAT ::=							ENUMERATED {
										dat1, dat2, dat3, dat4, dat5, dat6,
										dat7, dat8, dat9, dat10, dat15, dat20,
										dat25, dat30, dat35, dat40 }

MaxDAT-Retransmissions ::=			SEQUENCE {
	maxDAT								MaxDAT,
	timerMRW							TimerMRW,
	maxMRW								MaxMRW
}

MaxMRW ::=							ENUMERATED {
										mm1, mm4, mm6, mm8, mm12, mm16,
										mm24, mm32 }

MaxPDCP-SN-WindowSize ::=			ENUMERATED {
										sn255, sn65535 }

MaxRST ::=							ENUMERATED {
										rst1, rst4, rst6, rst8, rst12,
										rst16, rst24, rst32 }

NoExplicitDiscard ::=				ENUMERATED {
										dt10, dt20, dt30, dt40, dt50,
										dt60, dt70, dt80, dt90, dt100 }

PDCP-Info ::=						SEQUENCE {
	losslessSRNS-RelocSupport			LosslessSRNS-RelocSupport			OPTIONAL,
	-- TABULAR: pdcp-PDU-Header is MD in the tabular format and it can be encoded
	-- in one bit, so the OPTIONAL is removed for compactness.
	pdcp-PDU-Header						PDCP-PDU-Header,
	headerCompressionInfoList			HeaderCompressionInfoList			OPTIONAL
}

PDCP-InfoReconfig ::=				SEQUENCE {
	pdcp-Info							PDCP-Info,
	-- dummy is not used in this version of the specification and
	-- it should be ignored.
	dummy								INTEGER (0..65535)
}

PDCP-PDU-Header ::=					ENUMERATED {
										present, absent }

PDCP-SN-Info ::=					INTEGER (0..65535)

Poll-PDU ::=						ENUMERATED {
										pdu1, pdu2, pdu4, pdu8, pdu16,
										pdu32, pdu64, pdu128 }

Poll-SDU ::=						ENUMERATED {
										sdu1, sdu4, sdu16, sdu64 }

PollingInfo ::=						SEQUENCE {
	timerPollProhibit					TimerPollProhibit					OPTIONAL,
	timerPoll							TimerPoll							OPTIONAL,
	poll-PDU							Poll-PDU							OPTIONAL,
	poll-SDU							Poll-SDU							OPTIONAL,
	lastTransmissionPDU-Poll			BOOLEAN,
	lastRetransmissionPDU-Poll			BOOLEAN,
	pollWindow							PollWindow							OPTIONAL,
	timerPollPeriodic					TimerPollPeriodic					OPTIONAL
}

PollWindow ::=						ENUMERATED {
										pw50, pw60, pw70, pw80, pw85,
										pw90, pw95, pw99 }

PredefinedConfigIdentity ::=		INTEGER (0..15)

PredefinedConfigValueTag ::=		INTEGER (0..15)

PredefinedRB-Configuration ::=		SEQUENCE {
	re-EstablishmentTimer				Re-EstablishmentTimer,
	srb-InformationList					SRB-InformationSetupList,
	rb-InformationList					RB-InformationSetupList
}

PreDefRadioConfiguration ::=		SEQUENCE {
	-- Radio bearer IEs
	predefinedRB-Configuration			PredefinedRB-Configuration,
	-- Transport channel IEs
	preDefTransChConfiguration			PreDefTransChConfiguration,
	-- Physical channel IEs
	preDefPhyChConfiguration			PreDefPhyChConfiguration
}

PredefinedConfigStatusList ::=				SEQUENCE (SIZE (maxPredefConfig)) OF
											PredefinedConfigStatusInfo

PredefinedConfigStatusInfo::=		CHOICE {
	storedWithValueTagSameAsPrevius		NULL,
	other								CHOICE {
		notStored							NULL,
		storedWithDifferentValueTag			PredefinedConfigValueTag
	}
}

RAB-Info ::=						SEQUENCE {
	rab-Identity						RAB-Identity,
	cn-DomainIdentity					CN-DomainIdentity,
	nas-Synchronisation-Indicator		NAS-Synchronisation-Indicator	OPTIONAL,
	re-EstablishmentTimer				Re-EstablishmentTimer
}
RAB-InformationList			::=		SEQUENCE (SIZE (1..maxRABsetup)) OF
										RAB-Info

RAB-InformationReconfigList ::=	SEQUENCE (SIZE (1.. maxRABsetup)) OF
										RAB-InformationReconfig

RAB-InformationReconfig ::=			SEQUENCE {
	rab-Identity						RAB-Identity,
	cn-DomainIdentity					CN-DomainIdentity,
	nas-Synchronisation-Indicator		NAS-Synchronisation-Indicator
}

RAB-Info-Post ::=						SEQUENCE {
	rab-Identity						RAB-Identity,
	cn-DomainIdentity					CN-DomainIdentity,
	nas-Synchronisation-Indicator		NAS-Synchronisation-Indicator	OPTIONAL
}

RAB-InformationSetup ::=			SEQUENCE {
	rab-Info							RAB-Info,
	rb-InformationSetupList				RB-InformationSetupList
}

RAB-InformationSetupList ::=		SEQUENCE (SIZE (1..maxRABsetup)) OF
										RAB-InformationSetup

RB-ActivationTimeInfo ::=			SEQUENCE {
	rb-Identity							RB-Identity,
	rlc-SequenceNumber					RLC-SequenceNumber
}	

RB-ActivationTimeInfoList ::=		SEQUENCE (SIZE (1..maxRB)) OF
										RB-ActivationTimeInfo

RB-COUNT-C-Information ::=			SEQUENCE {
	rb-Identity							RB-Identity,
	count-C-UL							COUNT-C,
	count-C-DL							COUNT-C
}

RB-COUNT-C-InformationList ::=		SEQUENCE (SIZE (1..maxRBallRABs)) OF
										RB-COUNT-C-Information

RB-COUNT-C-MSB-Information ::=		SEQUENCE {
	rb-Identity							RB-Identity,
	count-C-MSB-UL						COUNT-C-MSB,
	count-C-MSB-DL						COUNT-C-MSB
}

RB-COUNT-C-MSB-InformationList ::=	SEQUENCE (SIZE (1..maxRBallRABs)) OF
										RB-COUNT-C-MSB-Information

RB-Identity ::=						INTEGER (1..32)

RB-IdentityList ::=					SEQUENCE (SIZE (1..maxRB)) OF
										RB-Identity

RB-InformationAffected ::=			SEQUENCE {
	rb-Identity							RB-Identity,
	rb-MappingInfo						RB-MappingInfo
}

RB-InformationAffectedList ::=		SEQUENCE (SIZE (1..maxRB)) OF
										RB-InformationAffected

RB-InformationReconfig ::=			SEQUENCE {
	rb-Identity							RB-Identity,
	pdcp-Info							PDCP-InfoReconfig					OPTIONAL,
	pdcp-SN-Info						PDCP-SN-Info						OPTIONAL,
	rlc-Info							RLC-Info							OPTIONAL,
	rb-MappingInfo						RB-MappingInfo						OPTIONAL,
	rb-StopContinue						RB-StopContinue					OPTIONAL
}

RB-InformationReconfigList ::=		SEQUENCE (SIZE (1..maxRB)) OF
										RB-InformationReconfig

RB-InformationReleaseList ::=		SEQUENCE (SIZE (1..maxRB)) OF
										RB-Identity

RB-InformationSetup ::=				SEQUENCE {
	rb-Identity							RB-Identity,
	pdcp-Info							PDCP-Info							OPTIONAL,
	rlc-InfoChoice						RLC-InfoChoice,
	rb-MappingInfo						RB-MappingInfo
}

RB-InformationSetupList ::=			SEQUENCE (SIZE (1..maxRBperRAB)) OF
										RB-InformationSetup

RB-MappingInfo ::=					SEQUENCE (SIZE (1..maxRBMuxOptions)) OF
										RB-MappingOption

RB-MappingOption ::=				SEQUENCE {
	ul-LogicalChannelMappings			UL-LogicalChannelMappings			OPTIONAL,
	dl-LogicalChannelMappingList		DL-LogicalChannelMappingList		OPTIONAL
}

RB-StopContinue ::=					ENUMERATED {
										stopRB, continueRB }

RB-WithPDCP-Info ::=				SEQUENCE {
	rb-Identity							RB-Identity,
	pdcp-SN-Info						PDCP-SN-Info
}

RB-WithPDCP-InfoList ::=			SEQUENCE (SIZE (1..maxRBallRABs)) OF
										RB-WithPDCP-Info

ReceivingWindowSize ::=				ENUMERATED {
										rw1, rw8, rw16, rw32, rw64, rw128, rw256,
										rw512, rw768, rw1024, rw1536, rw2047,
										rw2560, rw3072, rw3584, rw4095 }

RFC2507-Info ::=					SEQUENCE {
	f-MAX-PERIOD						INTEGER (1..65535)					DEFAULT 256,
	f-MAX-TIME							INTEGER (1..255)					DEFAULT 5,
	max-HEADER							INTEGER (60..65535)					DEFAULT 168,
	tcp-SPACE							INTEGER (3..255)					DEFAULT 15,
	non-TCP-SPACE						INTEGER (3..65535)					DEFAULT 15,
	-- TABULAR: expectReordering has only two possible values, so using Optional or Default
	-- would be wasteful
	expectReordering					ExpectReordering
}

RLC-Info ::=						SEQUENCE {
	ul-RLC-Mode							UL-RLC-Mode							OPTIONAL,
	dl-RLC-Mode							DL-RLC-Mode							OPTIONAL
}

RLC-InfoChoice ::=					CHOICE {
	rlc-Info							RLC-Info,
	same-as-RB							RB-Identity
}

RLC-SequenceNumber ::=				INTEGER (0..4095)

RLC-SizeInfo	::=					SEQUENCE {
	rlc-SizeIndex						INTEGER (1..maxTF)
}

RLC-SizeExplicitList	::=			SEQUENCE (SIZE	(1..maxTF))	OF
										RLC-SizeInfo

SRB-InformationSetup ::=			SEQUENCE {
	-- The default value for rb-Identity is the smallest value not used yet.
	rb-Identity							RB-Identity							OPTIONAL,
	rlc-InfoChoice						RLC-InfoChoice,
	rb-MappingInfo						RB-MappingInfo
}

SRB-InformationSetupList ::=		SEQUENCE (SIZE (1..maxSRBsetup)) OF
										SRB-InformationSetup

SRB-InformationSetupList2 ::=		SEQUENCE (SIZE (3..4)) OF
										SRB-InformationSetup

TimerDiscard ::=					ENUMERATED {
										td0-1, td0-25, td0-5, td0-75,
										td1, td1-25, td1-5, td1-75,
										td2, td2-5, td3, td3-5, td4,
										td4-5, td5, td7-5 }

TimerEPC ::=						ENUMERATED {
										te50, te60, te70, te80, te90,
										te100, te120, te140, te160, te180,
										te200, te300, te400, te500, te700,
										te900 }

TimerMRW ::=						ENUMERATED {
										te50, te60, te70, te80, te90, te100,
										te120, te140, te160, te180, te200,
										te300, te400, te500, te700, te900 }

TimerPoll ::=						ENUMERATED {
										tp10, tp20, tp30, tp40, tp50,
										tp60, tp70, tp80, tp90, tp100,
										tp110, tp120, tp130, tp140, tp150,
										tp160, tp170, tp180, tp190, tp200,
										tp210, tp220, tp230, tp240, tp250,
										tp260, tp270, tp280, tp290, tp300,
										tp310, tp320, tp330, tp340, tp350,
										tp360, tp370, tp380, tp390, tp400,
										tp410, tp420, tp430, tp440, tp450,
										tp460, tp470, tp480, tp490, tp500,
										tp510, tp520, tp530, tp540, tp550,
										tp600, tp650, tp700, tp750, tp800,
										tp850, tp900, tp950, tp1000 }

TimerPollPeriodic ::=				ENUMERATED {
										tper100, tper200, tper300, tper400,
										tper500, tper750, tper1000, tper2000 }

TimerPollProhibit ::=				ENUMERATED {
										tpp10, tpp20, tpp30, tpp40, tpp50,
										tpp60, tpp70, tpp80, tpp90, tpp100,
										tpp110, tpp120, tpp130, tpp140, tpp150,
										tpp160, tpp170, tpp180, tpp190, tpp200,
										tpp210, tpp220, tpp230, tpp240, tpp250,
										tpp260, tpp270, tpp280, tpp290, tpp300,
										tpp310, tpp320, tpp330, tpp340, tpp350,
										tpp360, tpp370, tpp380, tpp390, tpp400,
										tpp410, tpp420, tpp430, tpp440, tpp450,
										tpp460, tpp470, tpp480, tpp490, tpp500,
										tpp510, tpp520, tpp530, tpp540, tpp550,
										tpp600, tpp650, tpp700, tpp750, tpp800,
										tpp850, tpp900, tpp950, tpp1000 }

TimerRST ::=						ENUMERATED {
										tr50, tr100, tr150, tr200, tr250, tr300,
										tr350, tr400, tr450, tr500, tr550,
										tr600, tr700, tr800, tr900, tr1000 }

TimerStatusPeriodic ::=				ENUMERATED {
										tsp100, tsp200,	tsp300, tsp400, tsp500,
										tsp750, tsp1000, tsp2000 }

TimerStatusProhibit ::=				ENUMERATED {
										tsp10,tsp20,tsp30,tsp40,tsp50,
										tsp60,tsp70,tsp80,tsp90,tsp100,
										tsp110,tsp120,tsp130,tsp140,tsp150,
										tsp160,tsp170,tsp180,tsp190,tsp200,
										tsp210,tsp220,tsp230,tsp240,tsp250,
										tsp260,tsp270,tsp280,tsp290,tsp300,
										tsp310,tsp320,tsp330,tsp340,tsp350,
										tsp360,tsp370,tsp380,tsp390,tsp400,
										tsp410,tsp420,tsp430,tsp440,tsp450,
										tsp460,tsp470,tsp480,tsp490,tsp500,
										tsp510,tsp520,tsp530,tsp540,tsp550,
										tsp600,tsp650,tsp700,tsp750,tsp800,
										tsp850,tsp900,tsp950,tsp1000 }

TransmissionRLC-Discard ::=			CHOICE {
	timerBasedExplicit					ExplicitDiscard,
	timerBasedNoExplicit				NoExplicitDiscard,
	maxDAT-Retransmissions				MaxDAT-Retransmissions,
	noDiscard							MaxDAT
}

TransmissionWindowSize ::=			ENUMERATED {
										tw1, tw8, tw16, tw32, tw64, tw128, tw256,
										tw512, tw768, tw1024, tw1536, tw2047,
										tw2560, tw3072, tw3584, tw4095 }

UL-AM-RLC-Mode ::=					SEQUENCE {
	transmissionRLC-Discard				TransmissionRLC-Discard,
	transmissionWindowSize				TransmissionWindowSize,
	timerRST							TimerRST,
	max-RST								MaxRST,
	pollingInfo							PollingInfo							OPTIONAL
}

UL-CounterSynchronisationInfo ::=		SEQUENCE {
	rB-WithPDCP-InfoList					RB-WithPDCP-InfoList	OPTIONAL,
	startList								STARTList
}

UL-LogicalChannelMapping ::=		SEQUENCE {
	-- TABULAR: UL-TransportChannelType contains TransportChannelIdentity as well.
	ul-TransportChannelType				UL-TransportChannelType,
	logicalChannelIdentity				LogicalChannelIdentity				OPTIONAL,
	rlc-SizeList						CHOICE {
		allSizes							NULL,
		configured							NULL,
		explicitList						RLC-SizeExplicitList
	},
	mac-LogicalChannelPriority			MAC-LogicalChannelPriority
}

UL-LogicalChannelMappingList ::=	SEQUENCE {
	-- rlc-LogicalChannelMappingIndicator shall be set to TRUE in this version
	-- of the specification
	rlc-LogicalChannelMappingIndicator	BOOLEAN,
	ul-LogicalChannelMapping			SEQUENCE (SIZE (maxLoCHperRLC)) OF
										UL-LogicalChannelMapping
}

UL-LogicalChannelMappings ::=		CHOICE {
	oneLogicalChannel					UL-LogicalChannelMapping,
	twoLogicalChannels					UL-LogicalChannelMappingList
}

UL-RLC-Mode ::=						CHOICE {
	ul-AM-RLC-Mode						UL-AM-RLC-Mode,
	ul-UM-RLC-Mode						UL-UM-RLC-Mode,
	ul-TM-RLC-Mode						UL-TM-RLC-Mode,
	spare								NULL
}

UL-TM-RLC-Mode ::=					SEQUENCE {
	transmissionRLC-Discard				TransmissionRLC-Discard				OPTIONAL,
	segmentationIndication				BOOLEAN
}

UL-UM-RLC-Mode ::=					SEQUENCE {
	transmissionRLC-Discard				TransmissionRLC-Discard				OPTIONAL

}

UL-TransportChannelType ::=			CHOICE {
	dch									TransportChannelIdentity,
	rach								NULL,
	cpch								NULL,
	usch								TransportChannelIdentity
}

-- ***************************************************
--
--     TRANSPORT CHANNEL INFORMATION ELEMENTS (10.3.5)
--
-- ***************************************************

AllowedTFC-List ::=					SEQUENCE (SIZE (1..maxTFC)) OF
										TFC-Value

AllowedTFI-List ::=					SEQUENCE (SIZE (1..maxTF)) OF
										INTEGER (0..31)

BitModeRLC-SizeInfo ::=				CHOICE {
	sizeType1							INTEGER (0..127),
	-- Actual value sizeType2 = (part1 * 8) + 128 + part2
	sizeType2							SEQUENCE {
		part1								INTEGER (0..15),
		part2								INTEGER (1..7)					OPTIONAL
	},
	-- Actual value sizeType3 = (part1 * 16) + 256 + part2
	sizeType3							SEQUENCE {
		part1								INTEGER (0..47),
		part2								INTEGER (1..15)					OPTIONAL
	},
	-- Actual value sizeType4 = (part1 * 64) + 1024 + part2
	sizeType4							SEQUENCE {
		part1								INTEGER (0..62),
		part2								INTEGER (1..63)					OPTIONAL
	}
}

-- Actual value BLER-QualityValue = IE value * 0.1
BLER-QualityValue ::=				INTEGER (-63..0)

ChannelCodingType ::=				CHOICE {
	-- the option 'noCoding' is only used for TDD in this version of the specification,
	-- otherwise it should be ignored
	noCoding							NULL,
	convolutional						CodingRate,
	turbo								NULL
}

CodingRate ::=						ENUMERATED {
										half,
										third }

CommonDynamicTF-Info ::=			SEQUENCE {
	rlc-Size							CHOICE {
		fdd									SEQUENCE {
			octetModeRLC-SizeInfoType2			OctetModeRLC-SizeInfoType2
		},
		tdd									SEQUENCE {
			commonTDD-Choice					CHOICE {
				bitModeRLC-SizeInfo					BitModeRLC-SizeInfo,
				octetModeRLC-SizeInfoType1			OctetModeRLC-SizeInfoType1
			}
		}
	},
	numberOfTbSizeList				SEQUENCE (SIZE (1..maxTF)) OF		
											NumberOfTransportBlocks,
	logicalChannelList				LogicalChannelList
}

CommonDynamicTF-Info-DynamicTTI ::=	SEQUENCE {
	commonTDD-Choice					CHOICE {
		bitModeRLC-SizeInfo					BitModeRLC-SizeInfo,
		octetModeRLC-SizeInfoType1			OctetModeRLC-SizeInfoType1
	},
	numberOfTbSizeAndTTIList			NumberOfTbSizeAndTTIList,
	logicalChannelList					LogicalChannelList
}

CommonDynamicTF-InfoList ::=		SEQUENCE (SIZE (1..maxTF)) OF
										CommonDynamicTF-Info

CommonDynamicTF-InfoList-DynamicTTI ::= SEQUENCE (SIZE (1..maxTF)) OF
										CommonDynamicTF-Info-DynamicTTI

CommonTransChTFS ::=				SEQUENCE {
	tti									CHOICE {
		tti10								CommonDynamicTF-InfoList,
		tti20								CommonDynamicTF-InfoList,
		tti40								CommonDynamicTF-InfoList,
		tti80								CommonDynamicTF-InfoList,
		dynamic								CommonDynamicTF-InfoList-DynamicTTI
	},
	semistaticTF-Information			SemistaticTF-Information
}

CPCH-SetID ::=						INTEGER (1..maxCPCHsets)

CRC-Size ::=						ENUMERATED {
										crc0, crc8, crc12, crc16, crc24 }

DedicatedDynamicTF-Info ::=			SEQUENCE {
	rlc-Size							CHOICE {
		bitMode								BitModeRLC-SizeInfo,
		octetModeType1						OctetModeRLC-SizeInfoType1
	},
	numberOfTbSizeList				SEQUENCE (SIZE (1..maxTF)) OF										NumberOfTransportBlocks,
	logicalChannelList				LogicalChannelList
}

DedicatedDynamicTF-Info-DynamicTTI ::= SEQUENCE {
	rlc-Size							CHOICE {
		bitMode								BitModeRLC-SizeInfo,
		octetModeType1						OctetModeRLC-SizeInfoType1
	},
	numberOfTbSizeAndTTIList			NumberOfTbSizeAndTTIList,
	logicalChannelList				LogicalChannelList
}

DedicatedDynamicTF-InfoList ::=		SEQUENCE (SIZE (1..maxTF)) OF
										DedicatedDynamicTF-Info

DedicatedDynamicTF-InfoList-DynamicTTI ::= SEQUENCE (SIZE (1..maxTF)) OF
										DedicatedDynamicTF-Info-DynamicTTI

DedicatedTransChTFS ::=				SEQUENCE {
	tti									CHOICE {
		tti10								DedicatedDynamicTF-InfoList,
		tti20								DedicatedDynamicTF-InfoList,
		tti40								DedicatedDynamicTF-InfoList,
		tti80								DedicatedDynamicTF-InfoList,
		dynamic								DedicatedDynamicTF-InfoList-DynamicTTI
	},
	semistaticTF-Information			SemistaticTF-Information
}

-- The maximum allowed size of DL-AddReconfTransChInfo2List sequence is 16
DL-AddReconfTransChInfo2List ::=	SEQUENCE (SIZE (1..maxTrCHpreconf)) OF
										DL-AddReconfTransChInformation2

-- The maximum allowed size of DL-AddReconfTransChInfoList sequence is 16
DL-AddReconfTransChInfoList ::=		SEQUENCE (SIZE (1..maxTrCHpreconf)) OF
										DL-AddReconfTransChInformation

-- ASN.1 for IE "Added or Reconfigured DL TrCH information"
-- in case of messages other than: Radio Bearer Release message and
-- Radio Bearer Reconfiguration message
DL-AddReconfTransChInformation ::=	SEQUENCE {
	dl-TransportChannelType				DL-TrCH-Type,
	dl-transportChannelIdentity			TransportChannelIdentity,
	tfs-SignallingMode					CHOICE {
		explicit-config						TransportFormatSet,
		sameAsULTrCH						UL-TransportChannelIdentity
	},
	dch-QualityTarget					QualityTarget						OPTIONAL,
	-- dummy is not used in this version of the specification, it should
	-- not be sent and if received it should be ignored.
	dummy								TM-SignallingInfo					OPTIONAL
}

-- ASN.1 for IE "Added or Reconfigured DL TrCH information"
-- in case of Radio Bearer Release message and
-- Radio Bearer Reconfiguration message
DL-AddReconfTransChInformation2 ::= SEQUENCE {
	dl-TransportChannelType				DL-TrCH-Type,
	transportChannelIdentity			TransportChannelIdentity,
	tfs-SignallingMode					CHOICE {
		explicit-config						TransportFormatSet,
		sameAsULTrCH						UL-TransportChannelIdentity
	},
	qualityTarget						QualityTarget						OPTIONAL
}

DL-CommonTransChInfo ::=			SEQUENCE {
	sccpch-TFCS							TFCS								OPTIONAL,
	-- modeSpecificInfo should be optional. A new version of this IE should be defined
	-- to be used in later versions of messages using this IE
	modeSpecificInfo					CHOICE {
		fdd									SEQUENCE {
			dl-Parameters						CHOICE {
				dl-DCH-TFCS							TFCS,
				sameAsUL							NULL
			}																OPTIONAL
		},
		tdd									SEQUENCE {
			individualDL-CCTrCH-InfoList		IndividualDL-CCTrCH-InfoList
																			OPTIONAL
		}
	}
}

DL-DeletedTransChInfoList ::=		SEQUENCE (SIZE (1..maxTrCH)) OF
										DL-TransportChannelIdentity

DL-TransportChannelIdentity ::=		SEQUENCE {
	dl-TransportChannelType				DL-TrCH-Type,
	dl-TransportChannelIdentity			TransportChannelIdentity
}

DL-TrCH-Type ::= ENUMERATED {dch, dsch}

DRAC-ClassIdentity ::=				INTEGER (1..maxDRACclasses)

DRAC-StaticInformation ::=			SEQUENCE {
	transmissionTimeValidity			TransmissionTimeValidity,
	timeDurationBeforeRetry				TimeDurationBeforeRetry,
	drac-ClassIdentity					DRAC-ClassIdentity
}

DRAC-StaticInformationList ::=		SEQUENCE (SIZE (1..maxTrCH)) OF
										DRAC-StaticInformation

ExplicitTFCS-Configuration ::=		CHOICE {
	complete							TFCS-ReconfAdd,
	addition							TFCS-ReconfAdd,
	removal								TFCS-RemovalList,
	replacement							SEQUENCE {
		tfcsRemoval							TFCS-RemovalList,
		tfcsAdd								TFCS-ReconfAdd
	}
}

GainFactor ::=						INTEGER (0..15)

GainFactorInformation ::=			CHOICE {
	signalledGainFactors				SignalledGainFactors,
	computedGainFactors					ReferenceTFC-ID
}

IndividualDL-CCTrCH-Info ::=		SEQUENCE {
	dl-TFCS-Identity					TFCS-Identity,
	tfcs-SignallingMode					CHOICE {
		explicit-config						TFCS,
		sameAsUL							TFCS-Identity
	}
}

IndividualDL-CCTrCH-InfoList ::=	SEQUENCE (SIZE (1..maxCCTrCH)) OF
										IndividualDL-CCTrCH-Info

IndividualUL-CCTrCH-Info ::=		SEQUENCE {
	ul-TFCS-Identity					TFCS-Identity,
	ul-TFCS								TFCS,
	tfc-Subset							TFC-Subset
}

IndividualUL-CCTrCH-InfoList ::=	SEQUENCE (SIZE (1..maxCCTrCH)) OF
										IndividualUL-CCTrCH-Info

LogicalChannelByRB			::=		SEQUENCE {
	rb-Identity							RB-Identity,	
	logChOfRb							INTEGER (0..1)						OPTIONAL
}

LogicalChannelList	::=				CHOICE {
		allSizes							NULL,
		configured							NULL,
		explicitList						SEQUENCE (SIZE (1..15)) OF
												LogicalChannelByRB				
}

NumberOfTbSizeAndTTIList	::=		SEQUENCE (SIZE (1..maxTF)) OF SEQUENCE {
		numberOfTransportBlocks				NumberOfTransportBlocks,
		transmissionTimeInterval			TransmissionTimeInterval
}

MessType ::=						ENUMERATED {
										transportFormatCombinationControl }

Non-allowedTFC-List ::=				SEQUENCE (SIZE (1..maxTFC)) OF
										TFC-Value

NumberOfTransportBlocks::=			CHOICE {
	zero								NULL,
	one									NULL,
	small								INTEGER (2..17),
	large								INTEGER (18..512)
}

OctetModeRLC-SizeInfoType1 ::=		CHOICE {
	-- Actual size = (8 * sizeType1) + 16
	sizeType1							INTEGER (0..31),
	sizeType2							SEQUENCE {
		-- Actual size = (32 * part1) + 272 + (part2 * 8)
		part1								INTEGER (0..23),
		part2								INTEGER (1..3)					OPTIONAL
	},
	sizeType3							SEQUENCE {
		-- Actual size = (64 * part1) + 1040 + (part2 * 8)
		part1								INTEGER (0..61),
		part2								INTEGER (1..7)					OPTIONAL
	}
}

OctetModeRLC-SizeInfoType2 ::=		CHOICE {
	-- Actual size = (sizeType1 * 8) + 48
	sizeType1							INTEGER (0..31),
	-- Actual size = (sizeType2 * 16) + 312
	sizeType2							INTEGER (0..63),
	-- Actual size = (sizeType3 *64) + 1384
	sizeType3							INTEGER (0..56)
}

PowerOffsetInformation ::=			SEQUENCE {
	gainFactorInformation				GainFactorInformation,
	-- PowerOffsetPp-m is always absent in TDD
	powerOffsetPp-m						PowerOffsetPp-m						OPTIONAL
}

PowerOffsetPp-m ::=					INTEGER (-5..10)

PreDefTransChConfiguration ::=		SEQUENCE {
	ul-CommonTransChInfo				UL-CommonTransChInfo,
	ul-AddReconfTrChInfoList			UL-AddReconfTransChInfoList,
	dl-CommonTransChInfo				DL-CommonTransChInfo,
	dl-TrChInfoList						DL-AddReconfTransChInfoList
}	

QualityTarget ::=					SEQUENCE {
	bler-QualityValue					BLER-QualityValue
}

RateMatchingAttribute ::=			INTEGER (1..hiRM)


ReferenceTFC-ID ::=					INTEGER (0..3)

RestrictedTrChInfo ::=				SEQUENCE {
	ul-TransportChannelType				UL-TrCH-Type,
	restrictedTrChIdentity				TransportChannelIdentity,
	allowedTFI-List						AllowedTFI-List						OPTIONAL
}

RestrictedTrChInfoList ::=			SEQUENCE (SIZE (1..maxTrCH)) OF
										RestrictedTrChInfo

SemistaticTF-Information ::=		SEQUENCE {
	-- TABULAR: Transmission time interval has been included in the IE CommonTransChTFS.
	channelCodingType					ChannelCodingType,
	rateMatchingAttribute				RateMatchingAttribute,
	crc-Size							CRC-Size
}

SignalledGainFactors ::=			SEQUENCE {
	modeSpecificInfo					CHOICE {
		fdd									SEQUENCE {
			gainFactorBetaC						GainFactor
		},
		tdd									NULL
	},
	gainFactorBetaD						GainFactor,
	referenceTFC-ID						ReferenceTFC-ID						OPTIONAL
}

SplitTFCI-Signalling ::=			SEQUENCE {
	splitType							SplitType						OPTIONAL,
	tfci-Field2-Length					INTEGER (1..10)					OPTIONAL,
	tfci-Field1-Information				ExplicitTFCS-Configuration		OPTIONAL,
	tfci-Field2-Information				TFCI-Field2-Information			OPTIONAL
}

SplitType ::=						ENUMERATED {
										hardSplit, logicalSplit }

TFC-Subset ::=						CHOICE {
	minimumAllowedTFC-Number			TFC-Value,
	allowedTFC-List						AllowedTFC-List,
	non-allowedTFC-List					Non-allowedTFC-List,
	restrictedTrChInfoList				RestrictedTrChInfoList,
	fullTFCS							NULL
}

TFC-Value ::=						INTEGER (0..1023)

TFCI-Field2-Information ::=			CHOICE {
	tfci-Range							TFCI-RangeList,
	explicit-config						ExplicitTFCS-Configuration
}

TFCI-Range ::=						SEQUENCE {
	maxTFCIField2Value					INTEGER (1..1023),
	tfcs-InfoForDSCH					TFCS-InfoForDSCH
}

TFCI-RangeList ::=					SEQUENCE (SIZE (1..maxPDSCH-TFCIgroups)) OF
										TFCI-Range

TFCS ::=							CHOICE {
	normalTFCI-Signalling				ExplicitTFCS-Configuration,
	splitTFCI-Signalling				SplitTFCI-Signalling
}

TFCS-Identity ::=					SEQUENCE {
	tfcs-ID								TFCS-IdentityPlain						DEFAULT 1,
	sharedChannelIndicator				BOOLEAN
}

TFCS-IdentityPlain ::=				INTEGER (1..8)

TFCS-InfoForDSCH ::=				CHOICE {
	ctfc2bit							INTEGER (0..3),
	ctfc4bit							INTEGER (0..15),
	ctfc6bit							INTEGER (0..63),
	ctfc8bit							INTEGER (0..255),
	ctfc12bit							INTEGER (0..4095),
	ctfc16bit							INTEGER (0..65535),
	ctfc24bit							INTEGER (0..16777215)
}

TFCS-ReconfAdd ::=					SEQUENCE{
	ctfcSize							CHOICE{
		ctfc2Bit							SEQUENCE (SIZE (1..maxTFC)) OF SEQUENCE {
			ctfc2								INTEGER (0..3),
			powerOffsetInformation				PowerOffsetInformation			OPTIONAL
		},
		ctfc4Bit							SEQUENCE (SIZE (1..maxTFC)) OF SEQUENCE {
			ctfc4								INTEGER (0..15),
			powerOffsetInformation				PowerOffsetInformation			OPTIONAL
		},
		ctfc6Bit							SEQUENCE (SIZE (1..maxTFC)) OF SEQUENCE {
			ctfc6								INTEGER (0..63),
			powerOffsetInformation				PowerOffsetInformation			OPTIONAL
		},
		ctfc8Bit							SEQUENCE (SIZE (1..maxTFC)) OF SEQUENCE {
			ctfc8								INTEGER (0..255),
			powerOffsetInformation				PowerOffsetInformation			OPTIONAL
		},
		ctfc12Bit							SEQUENCE (SIZE(1..maxTFC)) OF SEQUENCE {
			ctfc12								INTEGER (0..4095),
			powerOffsetInformation				PowerOffsetInformation			OPTIONAL
		},
		ctfc16Bit							SEQUENCE (SIZE (1..maxTFC)) OF SEQUENCE {
			ctfc16								INTEGER(0..65535),
			powerOffsetInformation				PowerOffsetInformation			OPTIONAL
		},
		ctfc24Bit							SEQUENCE (SIZE (1..maxTFC)) OF SEQUENCE {
			ctfc24								INTEGER(0..16777215),
			powerOffsetInformation				PowerOffsetInformation			OPTIONAL
		}
	}
}

TFCS-Removal ::=					SEQUENCE {
	tfci								INTEGER (0..1023)
}

TFCS-RemovalList ::=				SEQUENCE (SIZE (1..maxTFC)) OF
										TFCS-Removal

TimeDurationBeforeRetry ::=			INTEGER (1..256)

TM-SignallingInfo	::=				SEQUENCE {
	messType							MessType,
	tm-SignallingMode					CHOICE {
		mode1								NULL,
		mode2								SEQUENCE {
			-- In ul-controlledTrChList, TrCH-Type is always DCH
			ul-controlledTrChList				UL-ControlledTrChList
		}
	}
}

TransmissionTimeInterval ::=		ENUMERATED {
										tti10, tti20, tti40, tti80 }

TransmissionTimeValidity ::=		INTEGER (1..256)

TransportChannelIdentity ::=		INTEGER (1..32)

TransportChannelIdentityDCHandDSCH	::=	SEQUENCE {
	dch-transport-ch-id				TransportChannelIdentity,
	dsch-transport-ch-id			TransportChannelIdentity
}

TransportFormatSet ::=				CHOICE {
	dedicatedTransChTFS					DedicatedTransChTFS,
	commonTransChTFS					CommonTransChTFS
}

-- The maximum allowed size of UL-AddReconfTransChInfoList sequence is 16
UL-AddReconfTransChInfoList ::=		SEQUENCE (SIZE (1..maxTrCHpreconf)) OF
										UL-AddReconfTransChInformation

UL-AddReconfTransChInformation ::= SEQUENCE {
	ul-TransportChannelType				UL-TrCH-Type,
	transportChannelIdentity			TransportChannelIdentity,
	transportFormatSet					TransportFormatSet
}

UL-CommonTransChInfo ::=			SEQUENCE {
	-- tfc-Subset is applicable to FDD only, TDD specifies tfc-subset in
	-- individual CCTrCH Info
	tfc-Subset							TFC-Subset							OPTIONAL,
	prach-TFCS							TFCS								OPTIONAL,
	modeSpecificInfo					CHOICE {
		fdd									SEQUENCE {
			ul-TFCS							TFCS
		},
		tdd									SEQUENCE {

			individualUL-CCTrCH-InfoList		IndividualUL-CCTrCH-InfoList
																			OPTIONAL
		}
	}																		OPTIONAL
}

-- in UL-ControlledTrChList TrCH-Type is always DCH
UL-ControlledTrChList ::=			SEQUENCE (SIZE (1..maxTrCH)) OF
										TransportChannelIdentity

UL-DeletedTransChInfoList ::=		SEQUENCE (SIZE (1..maxTrCH)) OF
										UL-TransportChannelIdentity

UL-TransportChannelIdentity ::=		SEQUENCE {
	ul-TransportChannelType				UL-TrCH-Type,
	ul-TransportChannelIdentity			TransportChannelIdentity
}

UL-TrCH-Type ::= ENUMERATED {dch, usch}

-- ***************************************************
--
--     PHYSICAL CHANNEL INFORMATION ELEMENTS (10.3.6)
--
-- ***************************************************

AC-To-ASC-Mapping ::=				INTEGER (0..7)

AC-To-ASC-MappingTable ::=			SEQUENCE (SIZE (maxASCmap)) OF
										AC-To-ASC-Mapping

AccessServiceClass-FDD ::=			SEQUENCE {
	availableSignatureStartIndex		INTEGER (0..15),
	availableSignatureEndIndex			INTEGER (0..15),

	assignedSubChannelNumber			BIT STRING {
											b3(0),
											b2(1),
											b1(2),
											b0(3)
											}	(SIZE(4))
}

AccessServiceClass-TDD ::=			SEQUENCE {
	channelisationCodeIndices			BIT STRING	{
											chCodeIndex7(0),
											chCodeIndex6(1),
											chCodeIndex5(2),
											chCodeIndex4(3),
											chCodeIndex3(4),
											chCodeIndex2(5),
											chCodeIndex1(6),
											chCodeIndex0(7)
											} (SIZE(8))				OPTIONAL,
	subchannelSize						CHOICE {
		size1								NULL,
		size2								SEQUENCE {
			-- subch0 means bitstring '01' in the tabular, subch1 means bitsring '10'
			subchannels							ENUMERATED	{ subch0, subch1 }	OPTIONAL
		},
		size4								SEQUENCE {
			subchannels							BIT STRING	{
													subCh3(0),
													subCh2(1),
													subCh1(2),
													subCh0(3)
													} (SIZE(4))		OPTIONAL
		},
		size8								SEQUENCE {
			subchannels							BIT STRING	{
													subCh7(0),
													subCh6(1),
													subCh5(2),
													subCh4(3),
													subCh3(4),
													subCh2(5),
													subCh1(6),
													subCh0(7)
													} (SIZE(8))		OPTIONAL
		}
	}
}

AICH-Info ::=						SEQUENCE {
	channelisationCode256				ChannelisationCode256,
	sttd-Indicator						BOOLEAN,
	aich-TransmissionTiming				AICH-TransmissionTiming
}

AICH-PowerOffset ::=				INTEGER (-22..5)

AICH-TransmissionTiming ::=			ENUMERATED {
										e0, e1 }

AllocationPeriodInfo ::=			SEQUENCE {
	allocationActivationTime			INTEGER (0..255),
	allocationDuration					INTEGER (1..256)
}
-- Actual value Alpha = IE value * 0.125
Alpha ::=							INTEGER (0..8)

AP-AICH-ChannelisationCode ::=		INTEGER (0..255)

AP-PreambleScramblingCode ::=		INTEGER (0..79)

AP-Signature ::=					INTEGER (0..15)

AP-Signature-VCAM ::=				SEQUENCE {
	ap-Signature						AP-Signature,
	availableAP-SubchannelList			AvailableAP-SubchannelList OPTIONAL
}

AP-Subchannel ::=					INTEGER (0..11)

ASCSetting-FDD ::=						SEQUENCE {
	-- TABULAR: accessServiceClass-FDD is MD in tabular description
	-- Default value is previous ASC
	-- If this is the first ASC, the default value is all available signature and sub-channels
	accessServiceClass-FDD					AccessServiceClass-FDD	OPTIONAL
}

ASCSetting-TDD ::=						SEQUENCE {
	-- TABULAR: accessServiceClass-TDD is MD in tabular description
	-- Default value is previous ASC
	-- If this is the first ASC, the default value is all available channelisation codes and
	-- all available sub-channels with subchannelSize=size1.
	accessServiceClass-TDD					AccessServiceClass-TDD	OPTIONAL
}

AvailableAP-Signature-VCAMList ::=	SEQUENCE (SIZE (1..maxPCPCH-APsig)) OF
										AP-Signature-VCAM

AvailableAP-SignatureList ::=		SEQUENCE (SIZE (1..maxPCPCH-APsig)) OF
										AP-Signature

AvailableAP-SubchannelList ::=		SEQUENCE (SIZE (1..maxPCPCH-APsubCh)) OF
										AP-Subchannel

AvailableMinimumSF-ListVCAM ::=		SEQUENCE (SIZE (1..maxPCPCH-SF)) OF
										AvailableMinimumSF-VCAM

AvailableMinimumSF-VCAM ::=			SEQUENCE {
	minimumSpreadingFactor				MinimumSpreadingFactor,
	nf-Max								NF-Max,
	maxAvailablePCPCH-Number			MaxAvailablePCPCH-Number,
	availableAP-Signature-VCAMList		AvailableAP-Signature-VCAMList
}

AvailableSignatures ::=			BIT STRING {
									signature15(0),
									signature14(1),
									signature13(2),
									signature12(3),
									signature11(4),
									signature10(5),
									signature9(6),
									signature8(7),
									signature7(8),
									signature6(9),
									signature5(10),
									signature4(11),
									signature3(12),
									signature2(13),
									signature1(14),
									signature0(15)
									}	(SIZE(16))

AvailableSubChannelNumbers ::=		BIT STRING {
										subCh11(0),
										subCh10(1),
										subCh9(2),
										subCh8(3),
										subCh7(4),
										subCh6(5),
										subCh5(6),
										subCh4(7),
										subCh3(8),
										subCh2(9),
										subCh1(10),
										subCh0(11)
										}	(SIZE(12))

BurstType ::=						ENUMERATED {
										type1, type2 }

CCTrCH-PowerControlInfo ::=			SEQUENCE {
	tfcs-Identity						TFCS-Identity						OPTIONAL,
	ul-DPCH-PowerControlInfo			UL-DPCH-PowerControlInfo
}

CD-AccessSlotSubchannel ::=			INTEGER (0..11)

CD-AccessSlotSubchannelList ::=		SEQUENCE (SIZE (1..maxPCPCH-CDsubCh)) OF
										CD-AccessSlotSubchannel

CD-CA-ICH-ChannelisationCode ::=	INTEGER (0..255)

CD-PreambleScramblingCode ::=		INTEGER (0..79)

CD-SignatureCode ::=				INTEGER (0..15)

CD-SignatureCodeList ::=			SEQUENCE (SIZE (1..maxPCPCH-CDsig)) OF
										CD-SignatureCode

CellAndChannelIdentity ::=			SEQUENCE {
	burstType							BurstType,
	midambleShift						MidambleShiftLong,
	timeslot							TimeslotNumber,
	cellParametersID					CellParametersID
	}

CellParametersID ::=				INTEGER (0..127)

Cfntargetsfnframeoffset ::=				INTEGER(0..255)

ChannelAssignmentActive ::=			CHOICE {
	notActive							NULL,
	isActive							AvailableMinimumSF-ListVCAM
}

ChannelisationCode256 ::=			INTEGER (0..255)

ChannelReqParamsForUCSM ::=			SEQUENCE {
	availableAP-SignatureList			AvailableAP-SignatureList,
	availableAP-SubchannelList			AvailableAP-SubchannelList			OPTIONAL
}

ClosedLoopTimingAdjMode ::=			ENUMERATED {
										slot1, slot2 }

CodeNumberDSCH ::=					INTEGER (0..255)

CodeRange ::=						SEQUENCE {
	pdsch-CodeMapList					PDSCH-CodeMapList
}

CodeWordSet ::=						ENUMERATED {
										longCWS,
										mediumCWS,
										shortCWS,
										ssdtOff }

CommonTimeslotInfo ::=				SEQUENCE {
	-- TABULAR: secondInterleavingMode is MD, but since it can be encoded in a single
	-- bit it is not defined as OPTIONAL.
	secondInterleavingMode				SecondInterleavingMode,
	tfci-Coding							TFCI-Coding							OPTIONAL,
	puncturingLimit						PuncturingLimit,
	repetitionPeriodAndLength			RepetitionPeriodAndLength			OPTIONAL
}

CommonTimeslotInfoSCCPCH ::=		SEQUENCE {
	-- TABULAR: secondInterleavingMode is MD, but since it can be encoded in a single
	-- bit it is not defined as OPTIONAL.
	secondInterleavingMode				SecondInterleavingMode,
	tfci-Coding							TFCI-Coding							OPTIONAL,
	puncturingLimit						PuncturingLimit,
	repetitionPeriodLengthAndOffset		RepetitionPeriodLengthAndOffset		OPTIONAL
}

ConstantValue ::=					INTEGER (-35..-10)

ConstantValueTdd ::=				INTEGER (-35..10)

CPCH-PersistenceLevels ::=			SEQUENCE {
	cpch-SetID							CPCH-SetID,
	dynamicPersistenceLevelTF-List		DynamicPersistenceLevelTF-List	
}

CPCH-PersistenceLevelsList ::=		SEQUENCE (SIZE (1..maxCPCHsets)) OF
										CPCH-PersistenceLevels

CPCH-SetInfo ::=					SEQUENCE {
	cpch-SetID							CPCH-SetID,
	transportFormatSet					TransportFormatSet,
	tfcs								TFCS,
	ap-PreambleScramblingCode			AP-PreambleScramblingCode,
	ap-AICH-ChannelisationCode			AP-AICH-ChannelisationCode,
	cd-PreambleScramblingCode			CD-PreambleScramblingCode,
	cd-CA-ICH-ChannelisationCode		CD-CA-ICH-ChannelisationCode,
	cd-AccessSlotSubchannelList			CD-AccessSlotSubchannelList			OPTIONAL,
	cd-SignatureCodeList				CD-SignatureCodeList				OPTIONAL,
	deltaPp-m							DeltaPp-m,
	ul-DPCCH-SlotFormat					UL-DPCCH-SlotFormat,
	n-StartMessage						N-StartMessage,
	n-EOT								N-EOT,
	-- TABULAR: VCAM info has been nested inside ChannelAssignmentActive,
	-- which in turn is mandatory since it's only a binary choice.
	channelAssignmentActive				ChannelAssignmentActive,
	cpch-StatusIndicationMode			CPCH-StatusIndicationMode,
	pcpch-ChannelInfoList				PCPCH-ChannelInfoList
}

CPCH-SetInfoList ::=				SEQUENCE (SIZE (1..maxCPCHsets)) OF
										CPCH-SetInfo

CPCH-StatusIndicationMode ::=		ENUMERATED {
										pa-mode,
										pamsf-mode }

CSICH-PowerOffset ::=				INTEGER (-10..5)

-- DefaultDPCH-OffsetValueFDD and DefaultDPCH-OffsetValueTDD corresponds to
-- IE "Default DPCH Offset Value" depending on the mode.
-- Actual value DefaultDPCH-OffsetValueFDD = IE value * 512
DefaultDPCH-OffsetValueFDD ::=		INTEGER (0..599)

DefaultDPCH-OffsetValueTDD ::=		INTEGER (0..7)

DeltaPp-m ::=						INTEGER (-10..10)

-- Actual value DeltaSIR = IE value * 0.1
DeltaSIR ::=						INTEGER (0..30)

DL-CCTrCh ::=						SEQUENCE {
	tfcs-ID								TFCS-IdentityPlain					DEFAULT 1,
	timeInfo							TimeInfo,
	commonTimeslotInfo					CommonTimeslotInfo					OPTIONAL,
	dl-CCTrCH-TimeslotsCodes			DownlinkTimeslotsCodes				OPTIONAL,
	ul-CCTrChTPCList					UL-CCTrChTPCList					OPTIONAL	
}

DL-CCTrChList ::=					SEQUENCE (SIZE (1..maxCCTrCH)) OF
										DL-CCTrCh

DL-CCTrChListToRemove ::=			SEQUENCE (SIZE (1..maxCCTrCH)) OF
										TFCS-IdentityPlain

DL-ChannelisationCode ::=			SEQUENCE {
	secondaryScramblingCode				SecondaryScramblingCode				OPTIONAL,
	sf-AndCodeNumber					SF512-AndCodeNumber,
	scramblingCodeChange				ScramblingCodeChange				OPTIONAL
}

DL-ChannelisationCodeList ::=		SEQUENCE (SIZE (1..maxDPCH-DLchan)) OF
										DL-ChannelisationCode

DL-CommonInformation ::=			SEQUENCE {
	dl-DPCH-InfoCommon					DL-DPCH-InfoCommon			OPTIONAL,
	modeSpecificInfo					CHOICE {
		fdd									SEQUENCE {
			defaultDPCH-OffsetValue				DefaultDPCH-OffsetValueFDD	OPTIONAL,
			dpch-CompressedModeInfo				DPCH-CompressedModeInfo		OPTIONAL,
			tx-DiversityMode					TX-DiversityMode			OPTIONAL,
			ssdt-Information					SSDT-Information			OPTIONAL
		},
		tdd									SEQUENCE {
			defaultDPCH-OffsetValue				DefaultDPCH-OffsetValueTDD	OPTIONAL
		}
	}
}

DL-CommonInformationPost ::=		SEQUENCE {
	dl-DPCH-InfoCommon					DL-DPCH-InfoCommonPost
}

DL-CommonInformationPredef ::=		SEQUENCE {
	dl-DPCH-InfoCommon					DL-DPCH-InfoCommonPredef	OPTIONAL
}

DL-CompressedModeMethod ::=			ENUMERATED {
										puncturing, sf-2,
										higherLayerScheduling }

DL-DPCH-InfoCommon ::=				SEQUENCE {
	cfnHandling							CHOICE {
		maintain							NULL,
		initialise							SEQUENCE {
			cfntargetsfnframeoffset				Cfntargetsfnframeoffset				OPTIONAL
		}
	},
	modeSpecificInfo					CHOICE {
		fdd								SEQUENCE {
			dl-DPCH-PowerControlInfo			DL-DPCH-PowerControlInfo			OPTIONAL,
			powerOffsetPilot-pdpdch				PowerOffsetPilot-pdpdch,
			dl-rate-matching-restriction		Dl-rate-matching-restriction		OPTIONAL,
			-- TABULAR: The number of pilot bits is nested inside the spreading factor
			spreadingFactorAndPilot				SF512-AndPilot,
			positionFixedOrFlexible				PositionFixedOrFlexible,
			tfci-Existence						BOOLEAN
		},
		tdd									SEQUENCE {
			dl-DPCH-PowerControlInfo			DL-DPCH-PowerControlInfo			OPTIONAL
		}
	}
}

DL-DPCH-InfoCommonPost ::=			SEQUENCE {
	dl-DPCH-PowerControlInfo			DL-DPCH-PowerControlInfo				OPTIONAL
}

DL-DPCH-InfoCommonPredef ::=		SEQUENCE {
	modeSpecificInfo					CHOICE {
		fdd									SEQUENCE {
			-- TABULAR: The number of pilot bits is nested inside the spreading factor
			spreadingFactorAndPilot				SF512-AndPilot,
			positionFixedOrFlexible				PositionFixedOrFlexible,
			tfci-Existence						BOOLEAN
		},
		tdd									SEQUENCE {
			commonTimeslotInfo					CommonTimeslotInfo
		}
	}
}

DL-DPCH-InfoPerRL ::=				CHOICE {
	fdd									SEQUENCE {
		pCPICH-UsageForChannelEst			PCPICH-UsageForChannelEst,
		dpch-FrameOffset					DPCH-FrameOffset,
		secondaryCPICH-Info					SecondaryCPICH-Info				OPTIONAL,
		dl-ChannelisationCodeList			DL-ChannelisationCodeList,
		tpc-CombinationIndex				TPC-CombinationIndex,
		ssdt-CellIdentity					SSDT-CellIdentity				OPTIONAL,
		closedLoopTimingAdjMode				ClosedLoopTimingAdjMode			OPTIONAL
	},
	tdd									SEQUENCE {
		dl-CCTrChListToEstablish			DL-CCTrChList					OPTIONAL,
		dl-CCTrChListToRemove				DL-CCTrChListToRemove			OPTIONAL
	}
}

DL-DPCH-InfoPerRL-PostFDD ::=								SEQUENCE {
		pCPICH-UsageForChannelEst				PCPICH-UsageForChannelEst,
		dl-ChannelisationCode					DL-ChannelisationCode,
		tpc-CombinationIndex					TPC-CombinationIndex
}

DL-DPCH-InfoPerRL-PostTDD ::=				SEQUENCE {
	dl-DPCH-TimeslotsCodes					DownlinkTimeslotsCodes
}

DL-DPCH-PowerControlInfo ::=			SEQUENCE {
	modeSpecificInfo						CHOICE {
		fdd										SEQUENCE {
			dpc-Mode								DPC-Mode
		},
		tdd										SEQUENCE {
			tpc-StepSizeTDD							TPC-StepSizeTDD			OPTIONAL
		}
	}
}

DL-FrameType ::=					ENUMERATED {
										dl-FrameTypeA, dl-FrameTypeB }

DL-InformationPerRL ::=				SEQUENCE {
	modeSpecificInfo					CHOICE {
		fdd									SEQUENCE {
			primaryCPICH-Info					PrimaryCPICH-Info,
			pdsch-SHO-DCH-Info					PDSCH-SHO-DCH-Info			OPTIONAL,
			pdsch-CodeMapping					PDSCH-CodeMapping			OPTIONAL
		},
		tdd									PrimaryCCPCH-Info
	},
	dl-DPCH-InfoPerRL					DL-DPCH-InfoPerRL					OPTIONAL,
	sccpch-InfoforFACH					SCCPCH-InfoForFACH					OPTIONAL
}

DL-InformationPerRL-List ::=		SEQUENCE (SIZE (1..maxRL)) OF
										DL-InformationPerRL

DL-InformationPerRL-ListPostFDD ::=	SEQUENCE (SIZE (1..maxRL)) OF
										DL-InformationPerRL-PostFDD

DL-InformationPerRL-PostFDD ::=		SEQUENCE {
	primaryCPICH-Info					PrimaryCPICH-Info,
	dl-DPCH-InfoPerRL					DL-DPCH-InfoPerRL-PostFDD
}

DL-InformationPerRL-PostTDD ::=		SEQUENCE {
	primaryCCPCH-Info					PrimaryCCPCH-InfoPost,
	dl-DPCH-InfoPerRL					DL-DPCH-InfoPerRL-PostTDD
}

DL-PDSCH-Information ::=			SEQUENCE {
	pdsch-SHO-DCH-Info					PDSCH-SHO-DCH-Info					OPTIONAL,
	pdsch-CodeMapping					PDSCH-CodeMapping					OPTIONAL
}

Dl-rate-matching-restriction ::=	SEQUENCE {
	restrictedTrCH-InfoList				RestrictedTrCH-InfoList				OPTIONAL
}

DL-TS-ChannelisationCode ::=		ENUMERATED {
										cc16-1, cc16-2, cc16-3, cc16-4,
										cc16-5, cc16-6, cc16-7, cc16-8,
										cc16-9, cc16-10, cc16-11, cc16-12,
										cc16-13, cc16-14, cc16-15, cc16-16 }

DL-TS-ChannelisationCodesShort ::=	SEQUENCE {
	codesRepresentation					CHOICE {
		consecutive							SEQUENCE {
			firstChannelisationCode				DL-TS-ChannelisationCode,
			lastChannelisationCode				DL-TS-ChannelisationCode
		},
		bitmap								BIT STRING {
												chCode16-SF16(0),
												chCode15-SF16(1),
												chCode14-SF16(2),
												chCode13-SF16(3),
												chCode12-SF16(4),
												chCode11-SF16(5),
												chCode10-SF16(6),
												chCode9-SF16(7),
												chCode8-SF16(8),
												chCode7-SF16(9),
												chCode6-SF16(10),
												chCode5-SF16(11),
												chCode4-SF16(12),
												chCode3-SF16(13),
												chCode2-SF16(14),
												chCode1-SF16(15)
												}	(SIZE (16))
	}
}

DownlinkAdditionalTimeslots ::=		SEQUENCE {
	parameters							CHOICE {
		sameAsLast							SEQUENCE {
			timeslotNumber						TimeslotNumber
		},
		newParameters						SEQUENCE {
			individualTimeslotInfo				IndividualTimeslotInfo,
			dl-TS-ChannelisationCodesShort		DL-TS-ChannelisationCodesShort
		}
	}
}

DownlinkTimeslotsCodes ::=		SEQUENCE {
	firstIndividualTimeslotInfo			IndividualTimeslotInfo,
	dl-TS-ChannelisationCodesShort		DL-TS-ChannelisationCodesShort,
	moreTimeslots						CHOICE {
		noMore								NULL,
		additionalTimeslots					CHOICE {
			consecutive							INTEGER (1..maxTS-1),
			timeslotList						SEQUENCE (SIZE (1..maxTS-1)) OF
													DownlinkAdditionalTimeslots
		}
	}
}

DPC-Mode ::=						ENUMERATED {
										singleTPC,
										tpcTripletInSoft }	

-- Actual value DPCCH-PowerOffset = IE value * 2.
DPCCH-PowerOffset ::=				INTEGER (-82..-3)


-- Actual value DPCCH-PowerOffset2 = 2 + (IE value * 4)
DPCCH-PowerOffset2 ::=				INTEGER (-28..-13)

DPCH-CompressedModeInfo ::=			SEQUENCE {
	tgp-SequenceList					TGP-SequenceList
}

DPCH-CompressedModeStatusInfo ::=	SEQUENCE {
	tgps-Reconfiguration-CFN			TGPS-Reconfiguration-CFN,
	tgp-SequenceShortList				SEQUENCE (SIZE (1..maxTGPS)) OF
											TGP-SequenceShort
}

TGPS-Reconfiguration-CFN ::=		INTEGER (0..255)

-- TABULAR: Actual value DPCH-FrameOffset = IE value * 256
DPCH-FrameOffset ::=				INTEGER (0..149)

DSCH-Mapping ::=					SEQUENCE {
	maxTFCI-Field2Value					MaxTFCI-Field2Value,
	spreadingFactor						SF-PDSCH,
	codeNumber							CodeNumberDSCH,
	multiCodeInfo						MultiCodeInfo
}

DSCH-MappingList ::=				SEQUENCE (SIZE (1..maxPDSCH-TFCIgroups)) OF
										DSCH-Mapping

DSCH-RadioLinkIdentifier ::=		INTEGER (0..511)

DurationTimeInfo ::=				INTEGER (1..4096)

DynamicPersistenceLevel ::=			INTEGER (1..8)

DynamicPersistenceLevelList ::=		SEQUENCE (SIZE (1..maxPRACH)) OF
										DynamicPersistenceLevel

DynamicPersistenceLevelTF-List ::= SEQUENCE (SIZE (1..maxTF-CPCH)) OF
										DynamicPersistenceLevel

FACH-PCH-Information ::=			SEQUENCE {
	transportFormatSet					TransportFormatSet,
	transportChannelIdentity			TransportChannelIdentity,
	ctch-Indicator						BOOLEAN
}

FACH-PCH-InformationList ::=		SEQUENCE (SIZE (1..maxFACHPCH)) OF
										FACH-PCH-Information

FrequencyInfo ::=					SEQUENCE {
	modeSpecificInfo					CHOICE {
		fdd									FrequencyInfoFDD,
		tdd									FrequencyInfoTDD	}
}

FrequencyInfoFDD ::=				SEQUENCE {
	uarfcn-UL							UARFCN				OPTIONAL,
	uarfcn-DL							UARFCN
}

FrequencyInfoTDD ::=				SEQUENCE {
	uarfcn-Nt							UARFCN
}

IndividualTimeslotInfo ::=			SEQUENCE {
	timeslotNumber						TimeslotNumber,
	tfci-Existence						BOOLEAN,
	midambleShiftAndBurstType			MidambleShiftAndBurstType
}

IndividualTS-Interference ::=		SEQUENCE {
	timeslot							TimeslotNumber,
	ul-TimeslotInterference				TDD-UL-Interference
}

IndividualTS-InterferenceList ::=	SEQUENCE (SIZE (1..maxTS)) OF
										IndividualTS-Interference

ITP ::=								ENUMERATED {
										mode0, mode1 }

NidentifyAbort ::=	INTEGER (1..128)

MaxAllowedUL-TX-Power ::=			INTEGER (-50..33)

MaxAvailablePCPCH-Number ::=		INTEGER (1..64)

MaxTFCI-Field2Value ::=				INTEGER (1..1023)

MidambleConfigurationBurstType1and3 ::= ENUMERATED {ms4, ms8, ms16}

MidambleConfigurationBurstType2 ::=		ENUMERATED {ms3, ms6}

MidambleShiftAndBurstType ::=		SEQUENCE {
	burstType							CHOICE {	
		type1								SEQUENCE {
			midambleConfigurationBurstType1and3	MidambleConfigurationBurstType1and3,
			midambleAllocationMode				CHOICE {
				defaultMidamble						NULL,
				commonMidamble						NULL,
				ueSpecificMidamble					SEQUENCE {
					midambleShift						MidambleShiftLong
				}
			}
		},
		type2								SEQUENCE {
			midambleConfigurationBurstType2		MidambleConfigurationBurstType2,
			midambleAllocationMode				CHOICE {
				defaultMidamble						NULL,
				commonMidamble						NULL,
				ueSpecificMidamble					SEQUENCE {
					midambleShift						MidambleShiftShort
				}
			}
		},
		type3								SEQUENCE {
			midambleConfigurationBurstType1and3	MidambleConfigurationBurstType1and3,
			midambleAllocationMode				CHOICE {
				defaultMidamble						NULL,
				ueSpecificMidamble					SEQUENCE {
					midambleShift						MidambleShiftLong
				}
			}
		}
	}
}

MidambleShiftLong ::=				INTEGER (0..15)


MidambleShiftShort ::=				INTEGER (0..5)

MinimumSpreadingFactor ::=			ENUMERATED {
										sf4, sf8, sf16, sf32,
										sf64, sf128, sf256 }

MultiCodeInfo ::=					INTEGER (1..16)


N-EOT ::=							INTEGER (0..7)

N-GAP ::=							ENUMERATED {
										f2, f4, f8 }

N-PCH ::=							INTEGER (1..8)

N-StartMessage ::=					INTEGER (1..8)

NB01 ::=							INTEGER (0..50)

NF-Max ::=							INTEGER (1..64)

NumberOfDPDCH ::=					INTEGER (1..maxDPDCH-UL)

NumberOfFBI-Bits ::=				INTEGER (1..2)

OpenLoopPowerControl-TDD ::=		SEQUENCE {
	primaryCCPCH-TX-Power				PrimaryCCPCH-TX-Power,
	alpha								Alpha						OPTIONAL,
	prach-ConstantValue					ConstantValueTdd,
	dpch-ConstantValue					ConstantValueTdd,
	pusch-ConstantValue					ConstantValueTdd			OPTIONAL
}
PagingIndicatorLength ::=			ENUMERATED {
										pi4, pi8, pi16 }

PC-Preamble ::=						INTEGER (0..7)

PCP-Length ::=						ENUMERATED {
										as0, as8 }

PCPCH-ChannelInfo ::=				SEQUENCE {
	pcpch-UL-ScramblingCode				INTEGER (0..79),
	pcpch-DL-ChannelisationCode			INTEGER (0..511),
	pcpch-DL-ScramblingCode				SecondaryScramblingCode				OPTIONAL,
	pcp-Length							PCP-Length,
	ucsm-Info							UCSM-Info							OPTIONAL
}

PCPCH-ChannelInfoList ::=			SEQUENCE (SIZE (1..maxPCPCHs)) OF
										PCPCH-ChannelInfo

PCPICH-UsageForChannelEst ::=		ENUMERATED {
										mayBeUsed,
										shallNotBeUsed }

PDSCH-CapacityAllocationInfo ::=	SEQUENCE {
	-- pdsch-PowerControlInfo is conditional on new-configuration branch below, if this
	-- selected the IE is OPTIONAL otherwise it should not be sent
	pdsch-PowerControlInfo				PDSCH-PowerControlInfo				OPTIONAL,
	pdsch-AllocationPeriodInfo			AllocationPeriodInfo,
	configuration						CHOICE {
		old-Configuration					SEQUENCE {
			tfcs-ID								TFCS-IdentityPlain					DEFAULT 1,
			pdsch-Identity						PDSCH-Identity
		},
		new-Configuration					SEQUENCE {
			pdsch-Info							PDSCH-Info,
			pdsch-Identity						PDSCH-Identity				OPTIONAL
		}
	}
}

PDSCH-CodeInfo ::=					SEQUENCE {
	spreadingFactor						SF-PDSCH,
	codeNumber							CodeNumberDSCH,
	multiCodeInfo						MultiCodeInfo
}

PDSCH-CodeInfoList ::=				SEQUENCE (SIZE (1..maxTFCI-2-Combs)) OF
										PDSCH-CodeInfo

PDSCH-CodeMap ::=					SEQUENCE {
	spreadingFactor						SF-PDSCH,
	multiCodeInfo						MultiCodeInfo,
	codeNumberStart						CodeNumberDSCH,
	codeNumberStop						CodeNumberDSCH
}

PDSCH-CodeMapList ::=				SEQUENCE (SIZE (1..maxPDSCH-TFCIgroups)) OF
										PDSCH-CodeMap

PDSCH-CodeMapping ::=				SEQUENCE {
	dl-ScramblingCode					SecondaryScramblingCode				OPTIONAL,
	signallingMethod					CHOICE {
		codeRange							CodeRange,
		tfci-Range							DSCH-MappingList,
		explicit-config						PDSCH-CodeInfoList,
		replace								ReplacedPDSCH-CodeInfoList
	}
}	

PDSCH-Identity ::=					INTEGER (1..hiPDSCHidentities)


PDSCH-Info ::=						SEQUENCE {
	tfcs-ID								TFCS-IdentityPlain					DEFAULT 1,
	commonTimeslotInfo					CommonTimeslotInfo					OPTIONAL,
	pdsch-TimeslotsCodes				DownlinkTimeslotsCodes				OPTIONAL
}

PDSCH-PowerControlInfo ::=			SEQUENCE {
	tpc-StepSizeTDD						TPC-StepSizeTDD						OPTIONAL,
	ul-CCTrChTPCList					UL-CCTrChTPCList					OPTIONAL
}

PDSCH-SHO-DCH-Info ::=				SEQUENCE {
	dsch-RadioLinkIdentifier			DSCH-RadioLinkIdentifier,
	rl-IdentifierList					RL-IdentifierList					OPTIONAL
}

PDSCH-SysInfo ::=					SEQUENCE {
	pdsch-Identity						PDSCH-Identity,
	pdsch-Info							PDSCH-Info,
	dsch-TFS							TransportFormatSet					OPTIONAL,
	dsch-TFCS							TFCS								OPTIONAL
}

PDSCH-SysInfoList ::=				SEQUENCE (SIZE (1..maxPDSCH)) OF
										PDSCH-SysInfo

PDSCH-SysInfoList-SFN ::=			SEQUENCE (SIZE (1..maxPDSCH)) OF
										SEQUENCE {
	pdsch-SysInfo							PDSCH-SysInfo,
	sfn-TimeInfo							SFN-TimeInfo					OPTIONAL
}

PersistenceScalingFactor ::=		ENUMERATED {
										psf0-9, psf0-8, psf0-7, psf0-6,
										psf0-5, psf0-4, psf0-3, psf0-2 }

PersistenceScalingFactorList ::=	SEQUENCE (SIZE (1..maxASCpersist)) OF
										PersistenceScalingFactor

PI-CountPerFrame ::=				ENUMERATED {
										e18, e36, e72, e144 }

PICH-Info ::=						CHOICE {
	fdd									SEQUENCE {
		channelisationCode256				ChannelisationCode256,
		pi-CountPerFrame					PI-CountPerFrame,
		sttd-Indicator						BOOLEAN
	},
	tdd									SEQUENCE {
		channelisationCode					TDD-PICH-CCode					OPTIONAL,
		timeslot							TimeslotNumber					OPTIONAL,
		midambleShiftAndBurstType			MidambleShiftAndBurstType,
		repetitionPeriodLengthOffset		RepPerLengthOffset-PICH			OPTIONAL,
		pagingIndicatorLength				PagingIndicatorLength			DEFAULT pi4,
		n-GAP								N-GAP							DEFAULT f4,
		n-PCH								N-PCH							DEFAULT 2
	}	
}

PICH-PowerOffset ::=				INTEGER (-10..5)

PilotBits128 ::=					ENUMERATED {
										pb4, pb8 }

PilotBits256 ::=					ENUMERATED {
										pb2, pb4, pb8 }

PositionFixedOrFlexible ::=			ENUMERATED {
										fixed,
										flexible }

PowerControlAlgorithm ::=			CHOICE {
	algorithm1							TPC-StepSizeFDD,
	algorithm2							NULL
}

PowerOffsetPilot-pdpdch ::=			INTEGER (0..24)

PowerRampStep ::=					INTEGER (1..8)

PRACH-Midamble ::=					ENUMERATED {
										direct,
										direct-Inverted }

PRACH-Partitioning ::=				CHOICE {
	fdd									SEQUENCE (SIZE (1..maxASC)) OF
	-- TABULAR: If only "NumASC+1" (with, NumASC+1 < maxASC) ASCSetting-FDD are listed, 
	-- the remaining (NumASC+2 through maxASC) ASCs are unspecified.
											ASCSetting-FDD,
	tdd									SEQUENCE (SIZE (1..maxASC)) OF
	-- TABULAR: If only "NumASC+1" (with, NumASC+1 < maxASC) ASCSetting-TDD are listed, 
	-- the remaining (NumASC+2 through maxASC) ASCs are unspecified.
											ASCSetting-TDD
}	

PRACH-PowerOffset ::=				SEQUENCE {
	powerRampStep						PowerRampStep,
	preambleRetransMax					PreambleRetransMax
}

PRACH-RACH-Info ::=					SEQUENCE {
	modeSpecificInfo					CHOICE {
		fdd									SEQUENCE {
			availableSignatures					AvailableSignatures,
			availableSF							SF-PRACH,
			preambleScramblingCodeWordNumber	PreambleScramblingCodeWordNumber,
			puncturingLimit						PuncturingLimit,
			availableSubChannelNumbers			AvailableSubChannelNumbers
		},
		tdd									SEQUENCE {
			timeslot							TimeslotNumber,
			channelisationCodeList				TDD-PRACH-CCodeList,
			prach-Midamble						PRACH-Midamble
		}
	}
}

PRACH-SystemInformation ::=			SEQUENCE {
	prach-RACH-Info						PRACH-RACH-Info,
	transportChannelIdentity			TransportChannelIdentity,
	rach-TransportFormatSet				TransportFormatSet					OPTIONAL,
	rach-TFCS							TFCS								OPTIONAL,
	prach-Partitioning					PRACH-Partitioning					OPTIONAL,
	persistenceScalingFactorList		PersistenceScalingFactorList		OPTIONAL,
	ac-To-ASC-MappingTable				AC-To-ASC-MappingTable				OPTIONAL,
	modeSpecificInfo					CHOICE {
		fdd									SEQUENCE {
			primaryCPICH-TX-Power				PrimaryCPICH-TX-Power		OPTIONAL,
			constantValue						ConstantValue				OPTIONAL,
			prach-PowerOffset					PRACH-PowerOffset			OPTIONAL,
			rach-TransmissionParameters			RACH-TransmissionParameters	OPTIONAL,
			aich-Info							AICH-Info					OPTIONAL
		},
		tdd									NULL
	}	
}

PRACH-SystemInformationList ::=		SEQUENCE (SIZE (1..maxPRACH)) OF
										PRACH-SystemInformation

PreambleRetransMax ::=				INTEGER (1..64)

PreambleScramblingCodeWordNumber ::=	INTEGER (0..15)

PreDefPhyChConfiguration ::=		SEQUENCE {
	ul-DPCH-InfoPredef					UL-DPCH-InfoPredef,
	dl-CommonInformationPredef			DL-CommonInformationPredef	OPTIONAL
}

PrimaryCCPCH-Info ::=				CHOICE {
	fdd									SEQUENCE {					
		tx-DiversityIndicator				BOOLEAN
	},
	tdd									SEQUENCE {
		syncCase							CHOICE {
			syncCase1							SEQUENCE {
				timeslot							TimeslotNumber					
			},
			syncCase2							SEQUENCE {
				timeslotSync2						TimeslotSync2
			}
		}																	OPTIONAL,
		cellParametersID					CellParametersID				OPTIONAL,
		sctd-Indicator						BOOLEAN
	}
}

PrimaryCCPCH-InfoPost ::=			SEQUENCE {
	syncCase							CHOICE {
		syncCase1							SEQUENCE {
			timeslot							TimeslotNumber					
		},
		syncCase2							SEQUENCE {
			timeslotSync2						TimeslotSync2
		}
	},
	cellParametersID					CellParametersID,
	sctd-Indicator						BOOLEAN
}

PrimaryCCPCH-TX-Power ::=			INTEGER (6..43)

PrimaryCPICH-Info ::=				SEQUENCE {
	primaryScramblingCode				PrimaryScramblingCode
}

PrimaryCPICH-TX-Power ::=			INTEGER (-10..50)

PrimaryScramblingCode ::=			INTEGER (0..511)

PuncturingLimit ::=					ENUMERATED {
										pl0-40, pl0-44, pl0-48, pl0-52, pl0-56,
										pl0-60, pl0-64, pl0-68, pl0-72, pl0-76,
										pl0-80, pl0-84, pl0-88, pl0-92, pl0-96, pl1 }

PUSCH-CapacityAllocationInfo ::=	SEQUENCE {
	pusch-Allocation					CHOICE {
		pusch-AllocationPending				NULL,
		pusch-AllocationAssignment			SEQUENCE {
			pusch-AllocationPeriodInfo			AllocationPeriodInfo,
			pusch-PowerControlInfo				UL-TargetSIR				OPTIONAL,
			configuration						CHOICE {
				old-Configuration					SEQUENCE {
					tfcs-ID								TFCS-IdentityPlain			DEFAULT 1,
					pusch-Identity						PUSCH-Identity
				},
				new-Configuration					SEQUENCE {
					pusch-Info							PUSCH-Info,
					pusch-Identity						PUSCH-Identity		OPTIONAL
				}
			}
		}
	}
}

PUSCH-Identity ::=					INTEGER (1..hiPUSCHidentities)

PUSCH-Info ::=						SEQUENCE {
	tfcs-ID								TFCS-IdentityPlain					DEFAULT 1,
	commonTimeslotInfo					CommonTimeslotInfo					OPTIONAL,
	pusch-TimeslotsCodes				UplinkTimeslotsCodes				OPTIONAL
}

PUSCH-SysInfo ::=					SEQUENCE {
	pusch-Identity						PUSCH-Identity,
	pusch-Info							PUSCH-Info,
	usch-TFS							TransportFormatSet					OPTIONAL,
	usch-TFCS							TFCS								OPTIONAL
}

PUSCH-SysInfoList ::=				SEQUENCE (SIZE (1..maxPUSCH)) OF
										PUSCH-SysInfo

PUSCH-SysInfoList-SFN ::=			SEQUENCE (SIZE (1..maxPUSCH)) OF
										SEQUENCE {
	pusch-SysInfo							PUSCH-SysInfo,
	sfn-TimeInfo							SFN-TimeInfo					OPTIONAL
}

RACH-TransmissionParameters ::=		SEQUENCE {
	mmax								INTEGER (1..32),
	nb01Min								NB01,
	nb01Max								NB01
}

ReducedScramblingCodeNumber ::=		INTEGER (0..8191)

RepetitionPeriodAndLength ::=		CHOICE {
	repetitionPeriod1					NULL,
	-- repetitionPeriod2 could just as well be NULL also
	repetitionPeriod2					INTEGER (1..1),
	repetitionPeriod4					INTEGER (1..3),
	repetitionPeriod8					INTEGER (1..7),
	repetitionPeriod16					INTEGER (1..15),
	repetitionPeriod32					INTEGER (1..31),
	repetitionPeriod64					INTEGER (1..63)
}

RepetitionPeriodLengthAndOffset ::= CHOICE {
	repetitionPeriod1					NULL,
	repetitionPeriod2					SEQUENCE {
		length								NULL,
		offset								INTEGER (0..1)
	},
	repetitionPeriod4					SEQUENCE {
		length								INTEGER (1..3),
		offset								INTEGER (0..3)
	},
	repetitionPeriod8					SEQUENCE {
		length								INTEGER (1..7),
		offset								INTEGER (0..7)
	},
	repetitionPeriod16					SEQUENCE {
		length								INTEGER (1..15),
		offset								INTEGER (0..15)
	},
	repetitionPeriod32					SEQUENCE {
		length								INTEGER (1..31),
		offset								INTEGER (0..31)
	},
	repetitionPeriod64					SEQUENCE {
		length								INTEGER (1..63),
		offset								INTEGER (0..63)
	}
}

ReplacedPDSCH-CodeInfo ::=			SEQUENCE {
	tfci-Field2							MaxTFCI-Field2Value,
	spreadingFactor						SF-PDSCH,
	codeNumber							CodeNumberDSCH,
	multiCodeInfo						MultiCodeInfo
}

ReplacedPDSCH-CodeInfoList ::=		SEQUENCE (SIZE (1..maxTFCI-2-Combs)) OF
										ReplacedPDSCH-CodeInfo

RepPerLengthOffset-PICH ::=			CHOICE {
	rpp4-2								INTEGER (0..3),
	rpp8-2								INTEGER (0..7),
	rpp8-4								INTEGER (0..7),
	rpp16-2								INTEGER (0..15),
	rpp16-4								INTEGER (0..15),
	rpp32-2								INTEGER (0..31),
	rpp32-4								INTEGER (0..31),
	rpp64-2								INTEGER (0..63),
	rpp64-4								INTEGER (0..63)
}

RestrictedTrCH ::=					SEQUENCE {
	dl-restrictedTrCh-Type				DL-TrCH-Type,
	restrictedDL-TrCH-Identity			TransportChannelIdentity,
	allowedTFIList						AllowedTFI-List
}

RestrictedTrCH-InfoList ::=			SEQUENCE (SIZE(1..maxTrCH)) OF
										RestrictedTrCH

RL-AdditionInformation ::=			SEQUENCE {
	primaryCPICH-Info					PrimaryCPICH-Info,
	dl-DPCH-InfoPerRL					DL-DPCH-InfoPerRL,
	tfci-CombiningIndicator				BOOLEAN,
	sccpch-InfoforFACH					SCCPCH-InfoForFACH					OPTIONAL
}

RL-AdditionInformationList ::=		SEQUENCE (SIZE (1..maxRL-1)) OF
										RL-AdditionInformation

RL-IdentifierList ::=				SEQUENCE (SIZE (1..maxRL)) OF
										PrimaryCPICH-Info

RL-RemovalInformationList ::=		SEQUENCE (SIZE (1..maxRL)) OF
										PrimaryCPICH-Info

RPP ::=								ENUMERATED {
										mode0, mode1 }

S-Field ::=							ENUMERATED {
										e1bit, e2bits }

SCCPCH-ChannelisationCode ::=		ENUMERATED {
										cc16-1, cc16-2, cc16-3, cc16-4,
										cc16-5, cc16-6, cc16-7, cc16-8,
										cc16-9, cc16-10, cc16-11, cc16-12,
										cc16-13, cc16-14, cc16-15, cc16-16 }

SCCPCH-ChannelisationCodeList ::=	SEQUENCE (SIZE (1..16)) OF
										SCCPCH-ChannelisationCode

SCCPCH-InfoForFACH ::=				SEQUENCE {
	secondaryCCPCH-Info					SecondaryCCPCH-Info,
	tfcs								TFCS,
	modeSpecificInfo				CHOICE {
		fdd								SEQUENCE {
			fach-PCH-InformationList			FACH-PCH-InformationList,
			sib-ReferenceListFACH				SIB-ReferenceListFACH
		},
		tdd								SEQUENCE {
			fach-PCH-InformationList			FACH-PCH-InformationList
		}
	}
}

SCCPCH-SystemInformation ::=		SEQUENCE {
	secondaryCCPCH-Info					SecondaryCCPCH-Info,
	tfcs								TFCS								OPTIONAL,
	fach-PCH-InformationList			FACH-PCH-InformationList			OPTIONAL,
	pich-Info							PICH-Info							OPTIONAL
}

SCCPCH-SystemInformationList ::=	SEQUENCE (SIZE (1..maxSCCPCH)) OF
										SCCPCH-SystemInformation

ScramblingCodeChange ::=			ENUMERATED {
										codeChange, noCodeChange }

ScramblingCodeType ::=				ENUMERATED {
										shortSC,
										longSC }

SecondaryCCPCH-Info ::=				SEQUENCE {
	modeSpecificInfo				CHOICE {
		fdd								SEQUENCE {
			-- dummy1 is not used in this version of the specification and should be ignored.
			dummy1							PCPICH-UsageForChannelEst,
			-- dummy2 is not used in this version of the specification. It should not
			-- be sent and if received it should be ignored.
			dummy2							SecondaryCPICH-Info				OPTIONAL,
			secondaryScramblingCode			SecondaryScramblingCode			OPTIONAL,
			sttd-Indicator					BOOLEAN,
			sf-AndCodeNumber				SF256-AndCodeNumber,
			pilotSymbolExistence			BOOLEAN,
			tfci-Existence					BOOLEAN,
			positionFixedOrFlexible			PositionFixedOrFlexible,
			timingOffset					TimingOffset					DEFAULT 0
		},
		tdd							SEQUENCE {
			-- TABULAR: the offset is included in CommonTimeslotInfoSCCPCH
			commonTimeslotInfo				CommonTimeslotInfoSCCPCH,
			individualTimeslotInfo			IndividualTimeslotInfo,
			channelisationCode				SCCPCH-ChannelisationCodeList
		}
	}
}

SecondaryCPICH-Info ::=				SEQUENCE {
	secondaryDL-ScramblingCode			SecondaryScramblingCode				OPTIONAL,
	channelisationCode					ChannelisationCode256
}

SecondaryScramblingCode ::=			INTEGER (1..15)

SecondInterleavingMode ::=			ENUMERATED {
										frameRelated, timeslotRelated }

-- SF256-AndCodeNumber encodes both "Spreading factor" and "Code Number"
SF256-AndCodeNumber ::=				CHOICE {
	sf4									INTEGER (0..3),
	sf8									INTEGER (0..7),
	sf16								INTEGER (0..15),
	sf32								INTEGER (0..31),
	sf64								INTEGER (0..63),
	sf128								INTEGER (0..127),
	sf256								INTEGER (0..255)
}

-- SF512-AndCodeNumber encodes both "Spreading factor" and "Code Number"
SF512-AndCodeNumber ::=				CHOICE {
	sf4									INTEGER (0..3),
	sf8									INTEGER (0..7),
	sf16								INTEGER (0..15),
	sf32								INTEGER (0..31),
	sf64								INTEGER (0..63),
	sf128								INTEGER (0..127),
	sf256								INTEGER (0..255),
	sf512								INTEGER (0..511)
}

-- SF512-AndPilot encodes both "Spreading factor" and "Number of bits for Pilot bits"
SF512-AndPilot ::=					CHOICE {
	sfd4								NULL,
	sfd8								NULL,
	sfd16								NULL,
	sfd32								NULL,
	sfd64								NULL,
	sfd128								PilotBits128,
	sfd256								PilotBits256,
	sfd512								NULL
}
SF-PDSCH ::=						ENUMERATED {
										sfp4, sfp8, sfp16, sfp32,
										sfp64, sfp128, sfp256 }

SF-PRACH ::=						ENUMERATED {
										sfpr32, sfpr64, sfpr128, sfpr256 }

SFN-TimeInfo ::=					SEQUENCE {
	activationTimeSFN					INTEGER (0..4095),
	physChDuration					DurationTimeInfo
}

SpecialBurstScheduling ::=				INTEGER (0..7)

SpreadingFactor::=					ENUMERATED {
										sf4, sf8, sf16, sf32,
										sf64, sf128, sf256 }

SRB-delay ::=						INTEGER (0..7)

SSDT-CellIdentity ::=				ENUMERATED {
										ssdt-id-a, ssdt-id-b, ssdt-id-c,
										ssdt-id-d, ssdt-id-e, ssdt-id-f,
										ssdt-id-g, ssdt-id-h }

SSDT-Information ::=				SEQUENCE {
	s-Field								S-Field,
	codeWordSet							CodeWordSet
}

TDD-PICH-CCode ::=					ENUMERATED {
										cc16-1, cc16-2, cc16-3, cc16-4,
										cc16-5, cc16-6, cc16-7, cc16-8,
										cc16-9, cc16-10, cc16-11, cc16-12,
										cc16-13, cc16-14, cc16-15, cc16-16 }

TDD-PRACH-CCode8 ::=				ENUMERATED {
										cc8-1, cc8-2, cc8-3, cc8-4,
										cc8-5, cc8-6, cc8-7, cc8-8 }

TDD-PRACH-CCode16 ::=				ENUMERATED {
										cc16-1, cc16-2, cc16-3, cc16-4,
										cc16-5, cc16-6, cc16-7, cc16-8,
										cc16-9, cc16-10, cc16-11, cc16-12,
										cc16-13, cc16-14, cc16-15, cc16-16 }

TDD-PRACH-CCodeList ::=			CHOICE {
	sf8									SEQUENCE (SIZE (1..8)) OF
											TDD-PRACH-CCode8,
	sf16								SEQUENCE (SIZE (1..8)) OF
											TDD-PRACH-CCode16
}

TFC-ControlDuration ::=				ENUMERATED {
										tfc-cd1, tfc-cd2, tfc-cd4, tfc-cd8,
										tfc-cd16, tfc-cd24, tfc-cd32,
										tfc-cd48, tfc-cd64, tfc-cd128,
										tfc-cd192, tfc-cd256, tfc-cd512 }

TFCI-Coding ::=						ENUMERATED {
										tfci-bits-4, tfci-bits-8,
										tfci-bits-16, tfci-bits-32 }

TGCFN ::=							INTEGER (0..255)

-- In TGD, value 270 represents "undefined" in the tabular description.
TGD ::=								INTEGER (15..270)

TGL ::=								INTEGER (1..14)

TGMP ::=							ENUMERATED {
										tdd-Measurement, fdd-Measurement,
										gsm-CarrierRSSIMeasurement,
										gsm-initialBSICIdentification, gsmBSICReconfirmation,
										multi-carrier }

TGP-Sequence ::=					SEQUENCE {
	tgpsi								TGPSI,
	tgps-Status							CHOICE {
		activate							SEQUENCE {
			tgcfn								TGCFN
		},
		deactivate							NULL
	},
	tgps-ConfigurationParams			TGPS-ConfigurationParams			OPTIONAL
}

TGP-SequenceList ::=				SEQUENCE (SIZE (1..maxTGPS)) OF
										TGP-Sequence

TGP-SequenceShort ::=				SEQUENCE {
	tgpsi								TGPSI,
	tgps-Status							CHOICE {
		activate							SEQUENCE {
			tgcfn								TGCFN
		},
		deactivate							NULL
	}
}

TGPL ::=							INTEGER (1..144)

-- TABULAR: In TGPRC, value 0 represents "infinity" in the tabular description.
TGPRC ::=							INTEGER (0..511)

TGPS-ConfigurationParams ::=		SEQUENCE {
	tgmp								TGMP,
	tgprc								TGPRC,
	tgsn								TGSN,
	tgl1								TGL,
	tgl2								TGL									OPTIONAL,
	tgd									TGD,
	tgpl1								TGPL,
	tgpl2								TGPL								OPTIONAL,
	rpp									RPP,
	itp									ITP,
	-- TABULAR: Compressed mode method is nested inside UL-DL-Mode
	ul-DL-Mode							UL-DL-Mode,
	dl-FrameType						DL-FrameType,
	deltaSIR1							DeltaSIR,
	deltaSIRAfter1						DeltaSIR,
	deltaSIR2							DeltaSIR							OPTIONAL,
	deltaSIRAfter2						DeltaSIR							OPTIONAL,
	nidentifyAbort						NidentifyAbort						OPTIONAL,
	treconfirmAbort						TreconfirmAbort						OPTIONAL
}

TGPSI ::=							INTEGER (1..maxTGPS)

TGSN ::=							INTEGER (0..14)

TimeInfo ::=						SEQUENCE {
	activationTime						ActivationTime						OPTIONAL,
	durationTimeInfo					DurationTimeInfo					OPTIONAL
}

TimeslotList ::=					SEQUENCE (SIZE (1..maxTS)) OF
										TimeslotNumber

TimeslotNumber ::=						INTEGER (0..14)

TimeslotSync2 ::=				INTEGER (0..6)

-- Actual value TimingOffset = IE value * 256
TimingOffset ::=					INTEGER (0..149)

TPC-CombinationIndex ::=			INTEGER (0..5)

-- Actual value TPC-StepSizeFDD = IE value + 1
TPC-StepSizeFDD ::=					INTEGER (0..1)

TPC-StepSizeTDD ::=					INTEGER (1..3)

-- Actual value TreconfirmAbort = IE value * 0.5 seconds
TreconfirmAbort ::=	INTEGER (1..20)

TX-DiversityMode ::=				ENUMERATED {
										noDiversity,
										sttd,
										closedLoopMode1,
										closedLoopMode2 }

UARFCN ::=						INTEGER (0..16383)

UCSM-Info ::=						SEQUENCE {
	minimumSpreadingFactor				MinimumSpreadingFactor,
	nf-Max								NF-Max,
	channelReqParamsForUCSM				ChannelReqParamsForUCSM
}

UL-CCTrCH ::=						SEQUENCE {
	tfcs-ID								TFCS-IdentityPlain					DEFAULT 1,
	ul-TargetSIR						UL-TargetSIR,
	timeInfo							TimeInfo,
	commonTimeslotInfo					CommonTimeslotInfo					OPTIONAL,
	ul-CCTrCH-TimeslotsCodes			UplinkTimeslotsCodes				OPTIONAL
}

UL-CCTrCHList ::=					SEQUENCE (SIZE (1..maxCCTrCH)) OF
										UL-CCTrCH

UL-CCTrCHListToRemove ::=			SEQUENCE (SIZE (1..maxCCTrCH)) OF
										TFCS-IdentityPlain

-- The size of UL-CCTrChTPCList should be from 1..maxCCTrCH
-- This should be corrected in a later release of the specification
UL-CCTrChTPCList ::=				SEQUENCE (SIZE (0..maxCCTrCH)) OF
											TFCS-Identity

UL-ChannelRequirement ::=			CHOICE {
	ul-DPCH-Info						UL-DPCH-Info,
	cpch-SetInfo						CPCH-SetInfo
}

UL-ChannelRequirementWithCPCH-SetID ::=	CHOICE {
	ul-DPCH-Info						UL-DPCH-Info,
	cpch-SetInfo						CPCH-SetInfo,
	cpch-SetID							CPCH-SetID
}

UL-CompressedModeMethod ::=			ENUMERATED {
										sf-2,
										higherLayerScheduling }

UL-DL-Mode ::=						CHOICE {
	ul									UL-CompressedModeMethod,
	dl									DL-CompressedModeMethod,
	ul-and-dl								SEQUENCE {
		ul									UL-CompressedModeMethod,
		dl									DL-CompressedModeMethod
	}
}

UL-DPCCH-SlotFormat ::=				ENUMERATED {
										slf0, slf1, slf2 }

UL-DPCH-Info ::=					SEQUENCE {
	ul-DPCH-PowerControlInfo			UL-DPCH-PowerControlInfo			OPTIONAL,
	modeSpecificInfo					CHOICE {
		fdd									SEQUENCE {
			scramblingCodeType					ScramblingCodeType,
			scramblingCode						UL-ScramblingCode,
			numberOfDPDCH						NumberOfDPDCH				DEFAULT 1,
			spreadingFactor						SpreadingFactor,
			tfci-Existence						BOOLEAN,
			-- numberOfFBI-Bits is conditional based on history
			numberOfFBI-Bits					NumberOfFBI-Bits			OPTIONAL,
			puncturingLimit						PuncturingLimit
		},
		tdd									SEQUENCE {
			ul-TimingAdvance					UL-TimingAdvanceControl		OPTIONAL,
			ul-CCTrCHList						UL-CCTrCHList				OPTIONAL,
			ul-CCTrCHListToRemove				UL-CCTrCHListToRemove		OPTIONAL
		}
	}
}

UL-DPCH-InfoPostFDD ::=				SEQUENCE {
	ul-DPCH-PowerControlInfo			UL-DPCH-PowerControlInfoPostFDD,
			scramblingCodeType					ScramblingCodeType,
			reducedScramblingCodeNumber			ReducedScramblingCodeNumber,
			spreadingFactor						SpreadingFactor

}

UL-DPCH-InfoPostTDD ::=				SEQUENCE {
	ul-DPCH-PowerControlInfo			UL-DPCH-PowerControlInfoPostTDD,
	ul-TimingAdvance					UL-TimingAdvanceControl					OPTIONAL,
	ul-CCTrCH-TimeslotsCodes			UplinkTimeslotsCodes
}

UL-DPCH-InfoPredef ::=				SEQUENCE {
	ul-DPCH-PowerControlInfo			UL-DPCH-PowerControlInfoPredef,
	modeSpecificInfo					CHOICE {
		fdd									SEQUENCE {
			tfci-Existence						BOOLEAN,
			puncturingLimit						PuncturingLimit
		},
		tdd									SEQUENCE {
			commonTimeslotInfo					CommonTimeslotInfo
		}
	}
}

UL-DPCH-PowerControlInfo ::=		CHOICE {
	fdd									SEQUENCE {
		dpcch-PowerOffset					DPCCH-PowerOffset,
		pc-Preamble							PC-Preamble,
		sRB-delay							SRB-delay,
		-- TABULAR: TPC step size nested inside PowerControlAlgorithm
		powerControlAlgorithm				PowerControlAlgorithm
	},
	tdd									SEQUENCE {
		ul-TargetSIR						UL-TargetSIR				OPTIONAL,
		ul-OL-PC-Signalling					CHOICE {
			broadcast-UL-OL-PC-info				NULL,
			handoverGroup						SEQUENCE {
				individualTS-InterferenceList		IndividualTS-InterferenceList,
				dpch-ConstantValue					ConstantValueTdd,
				primaryCCPCH-TX-Power				PrimaryCCPCH-TX-Power	
			}	
		}																OPTIONAL
	}
}

UL-DPCH-PowerControlInfoPostFDD ::=	SEQUENCE {
	-- DPCCH-PowerOffset2 has a smaller range to save bits
	dpcch-PowerOffset					DPCCH-PowerOffset2,
	pc-Preamble							PC-Preamble,
	sRB-delay							SRB-delay
}

UL-DPCH-PowerControlInfoPostTDD ::=	SEQUENCE {
	ul-TargetSIR						UL-TargetSIR,
	ul-TimeslotInterference				TDD-UL-Interference
}

UL-DPCH-PowerControlInfoPredef ::=		CHOICE {
	fdd									SEQUENCE {
		-- TABULAR: TPC step size nested inside PowerControlAlgorithm
		powerControlAlgorithm				PowerControlAlgorithm
	},
	tdd									SEQUENCE {
		dpch-ConstantValue					ConstantValueTdd
	}
}

UL-Interference ::=					INTEGER (-110..-70)

TDD-UL-Interference ::=				INTEGER (-110..-52)

UL-ScramblingCode ::=				INTEGER (0..16777215)

-- Actual value UL-TargetSIR = (IE value * 0.5) - 11
UL-TargetSIR ::=					INTEGER (0..62)

UL-TimingAdvance ::=				INTEGER (0..63)

UL-TimingAdvanceControl ::=			CHOICE {
	disabled							NULL,
	enabled								SEQUENCE {
		ul-TimingAdvance					UL-TimingAdvance				OPTIONAL,
		activationTime						ActivationTime					OPTIONAL
	}
}

UL-TS-ChannelisationCode ::=		ENUMERATED {
										cc1-1, cc2-1, cc2-2,
										cc4-1, cc4-2, cc4-3, cc4-4,
										cc8-1, cc8-2, cc8-3, cc8-4,
										cc8-5, cc8-6, cc8-7, cc8-8,
										cc16-1, cc16-2, cc16-3, cc16-4,
										cc16-5, cc16-6, cc16-7, cc16-8,
										cc16-9, cc16-10, cc16-11, cc16-12,
										cc16-13, cc16-14, cc16-15, cc16-16 }

UL-TS-ChannelisationCodeList ::=	SEQUENCE (SIZE (1..2)) OF
										UL-TS-ChannelisationCode

UplinkAdditionalTimeslots ::=		SEQUENCE {
	parameters							CHOICE {
		sameAsLast							SEQUENCE {
			timeslotNumber						TimeslotNumber
		},
		newParameters						SEQUENCE {
			individualTimeslotInfo						IndividualTimeslotInfo,
			ul-TS-ChannelisationCodeList				UL-TS-ChannelisationCodeList
		}
	}
}

UplinkTimeslotsCodes ::=			SEQUENCE {
	dynamicSFusage						BOOLEAN,
	firstIndividualTimeslotInfo			IndividualTimeslotInfo,
	ul-TS-ChannelisationCodeList		UL-TS-ChannelisationCodeList,
	moreTimeslots						CHOICE {
		noMore								NULL,
		additionalTimeslots					CHOICE {
			consecutive							SEQUENCE {
				numAdditionalTimeslots				INTEGER (1..maxTS-1)
			},
			timeslotList						SEQUENCE (SIZE (1..maxTS-1)) OF
													UplinkAdditionalTimeslots
		}
	}
}

-- ***************************************************
--
--     MEASUREMENT INFORMATION ELEMENTS (10.3.7)
--
-- ***************************************************

AcquisitionSatInfo ::=				SEQUENCE {
	satID								SatID,
	-- Actual value doppler0thOrder = IE value * 2.5
	doppler0thOrder						INTEGER (-2048..2047),
	extraDopplerInfo					ExtraDopplerInfo					OPTIONAL,
	codePhase							INTEGER (0..1022),
	integerCodePhase					INTEGER (0..19),
	gps-BitNumber						INTEGER (0..3),
	codePhaseSearchWindow				CodePhaseSearchWindow,
	azimuthAndElevation					AzimuthAndElevation					OPTIONAL
}	

AcquisitionSatInfoList ::=			SEQUENCE (SIZE (1..maxSat)) OF
										AcquisitionSatInfo


AdditionalMeasurementID-List ::=	SEQUENCE (SIZE (1..maxAdditionalMeas)) OF
										MeasurementIdentity

AlmanacSatInfo ::=					SEQUENCE {
	dataID								INTEGER (0..3),
	satID								SatID,
	e									BIT STRING (SIZE (16)),
	t-oa								BIT STRING (SIZE (8)),
	deltaI								BIT STRING (SIZE (16)),
	omegaDot							BIT STRING (SIZE (16)),
	satHealth							BIT STRING (SIZE (8)),
	a-Sqrt								BIT STRING (SIZE (24)),
	omega0								BIT STRING (SIZE (24)),
	m0									BIT STRING (SIZE (24)),
	omega								BIT STRING (SIZE (24)),
	af0									BIT STRING (SIZE (11)),
	af1									BIT STRING (SIZE (11))
}

AlmanacSatInfoList ::=				SEQUENCE (SIZE (1..maxSat)) OF
										AlmanacSatInfo

AverageRLC-BufferPayload ::=		ENUMERATED {
										pla0, pla4, pla8, pla16, pla32,
										pla64, pla128, pla256, pla512,
										pla1024, pla2k, pla4k, pla8k, pla16k,
										pla32k, pla64k, pla128k, pla256k,
										pla512k, pla1024k, spare12, spare11,
										spare10, spare9, spare8, spare7, spare6,
										spare5, spare4, spare3, spare2, spare1 }
	
AzimuthAndElevation ::=				SEQUENCE {
	-- Actual value azimuth = IE value * 11.25
	azimuth								INTEGER (0..31),
	-- Actual value elevation = IE value * 11.25
	elevation							INTEGER (0..7)
}

BadSatList ::=						SEQUENCE (SIZE (1..maxSat)) OF
										INTEGER (0..63)

Frequency-Band ::=					ENUMERATED {
										dcs1800BandUsed, pcs1900BandUsed }

BCCH-ARFCN ::=						INTEGER (0..1023)

BLER-MeasurementResults ::=			SEQUENCE {
	transportChannelIdentity			TransportChannelIdentity,
	dl-TransportChannelBLER				DL-TransportChannelBLER				OPTIONAL
}

BLER-MeasurementResultsList ::=		SEQUENCE (SIZE (1..maxTrCH)) OF
										BLER-MeasurementResults

BLER-TransChIdList ::=				SEQUENCE (SIZE (1..maxTrCH)) OF
										TransportChannelIdentity

BSIC-VerificationRequired ::=		ENUMERATED {
										required, notRequired }

BSICReported ::=					CHOICE {
	-- Value maxCellMeas is not allowed for verifiedBSIC
	verifiedBSIC						INTEGER (0..maxCellMeas),
	nonVerifiedBSIC						BCCH-ARFCN
}

BurstModeParameters ::=				SEQUENCE {
	burstStart							INTEGER (0..15),
	burstLength							INTEGER (10..25),
	burstFreq							INTEGER (1..16)
}

CellDCH-ReportCriteria ::=			CHOICE {
	intraFreqReportingCriteria			IntraFreqReportingCriteria,
	periodicalReportingCriteria			PeriodicalReportingCriteria
}

-- Actual value CellIndividualOffset = IE value * 0.5
CellIndividualOffset ::=			INTEGER (-20..20)

CellInfo ::=						SEQUENCE {
	cellIndividualOffset				CellIndividualOffset				DEFAULT 0,
	referenceTimeDifferenceToCell		ReferenceTimeDifferenceToCell		OPTIONAL,
	modeSpecificInfo					CHOICE {
		fdd									SEQUENCE {
			primaryCPICH-Info					PrimaryCPICH-Info			OPTIONAL,
			primaryCPICH-TX-Power				PrimaryCPICH-TX-Power		OPTIONAL,
			readSFN-Indicator					BOOLEAN,
			tx-DiversityIndicator				BOOLEAN		
		},
		tdd									SEQUENCE {
			primaryCCPCH-Info					PrimaryCCPCH-Info,
			primaryCCPCH-TX-Power				PrimaryCCPCH-TX-Power		OPTIONAL,
			timeslotInfoList					TimeslotInfoList			OPTIONAL,
			readSFN-Indicator					BOOLEAN
		}
	}
}

CellInfoSI-RSCP ::=					SEQUENCE {
	cellIndividualOffset				CellIndividualOffset				DEFAULT 0,
	referenceTimeDifferenceToCell		ReferenceTimeDifferenceToCell		OPTIONAL,
	modeSpecificInfo					CHOICE {
		fdd									SEQUENCE {
			primaryCPICH-Info					PrimaryCPICH-Info			OPTIONAL,
			primaryCPICH-TX-Power				PrimaryCPICH-TX-Power		OPTIONAL,
			readSFN-Indicator					BOOLEAN,
			tx-DiversityIndicator				BOOLEAN		
		},
		tdd									SEQUENCE {
			primaryCCPCH-Info					PrimaryCCPCH-Info,
			primaryCCPCH-TX-Power				PrimaryCCPCH-TX-Power		OPTIONAL,
			timeslotInfoList					TimeslotInfoList			OPTIONAL,
			readSFN-Indicator					BOOLEAN
		}
	},
	cellSelectionReselectionInfo		CellSelectReselectInfoSIB-11-12-RSCP		OPTIONAL
}

CellInfoSI-ECN0 ::=					SEQUENCE {
	cellIndividualOffset				CellIndividualOffset				DEFAULT 0,
	referenceTimeDifferenceToCell		ReferenceTimeDifferenceToCell		OPTIONAL,
	modeSpecificInfo					CHOICE {
		fdd									SEQUENCE {
			primaryCPICH-Info					PrimaryCPICH-Info			OPTIONAL,
			primaryCPICH-TX-Power				PrimaryCPICH-TX-Power		OPTIONAL,
			readSFN-Indicator					BOOLEAN,
			tx-DiversityIndicator				BOOLEAN		
		},
		tdd									SEQUENCE {
			primaryCCPCH-Info					PrimaryCCPCH-Info,
			primaryCCPCH-TX-Power				PrimaryCCPCH-TX-Power		OPTIONAL,
			timeslotInfoList					TimeslotInfoList			OPTIONAL,
			readSFN-Indicator					BOOLEAN
		}
	},
	cellSelectionReselectionInfo		CellSelectReselectInfoSIB-11-12-ECN0	OPTIONAL
}

CellInfoSI-HCS-RSCP ::=				SEQUENCE {
	cellIndividualOffset				CellIndividualOffset				DEFAULT 0,
	referenceTimeDifferenceToCell		ReferenceTimeDifferenceToCell		OPTIONAL,
	modeSpecificInfo					CHOICE {
		fdd									SEQUENCE {
			primaryCPICH-Info					PrimaryCPICH-Info			OPTIONAL,
			primaryCPICH-TX-Power				PrimaryCPICH-TX-Power		OPTIONAL,
			readSFN-Indicator					BOOLEAN,
			tx-DiversityIndicator				BOOLEAN		
		},
		tdd									SEQUENCE {
			primaryCCPCH-Info					PrimaryCCPCH-Info,
			primaryCCPCH-TX-Power				PrimaryCCPCH-TX-Power		OPTIONAL,
			timeslotInfoList					TimeslotInfoList			OPTIONAL,
			readSFN-Indicator					BOOLEAN
		}
	},
	cellSelectionReselectionInfo		CellSelectReselectInfoSIB-11-12-HCS-RSCP	OPTIONAL
}

CellInfoSI-HCS-ECN0 ::=				SEQUENCE {
	cellIndividualOffset				CellIndividualOffset				DEFAULT 0,
	referenceTimeDifferenceToCell		ReferenceTimeDifferenceToCell		OPTIONAL,
	modeSpecificInfo					CHOICE {
		fdd									SEQUENCE {
			primaryCPICH-Info					PrimaryCPICH-Info			OPTIONAL,
			primaryCPICH-TX-Power				PrimaryCPICH-TX-Power		OPTIONAL,
			readSFN-Indicator					BOOLEAN,
			tx-DiversityIndicator				BOOLEAN		
		},
		tdd									SEQUENCE {
			primaryCCPCH-Info					PrimaryCCPCH-Info,
			primaryCCPCH-TX-Power				PrimaryCCPCH-TX-Power		OPTIONAL,
			timeslotInfoList					TimeslotInfoList			OPTIONAL,
			readSFN-Indicator					BOOLEAN
		}
	},
	cellSelectionReselectionInfo		CellSelectReselectInfoSIB-11-12-HCS-ECN0	OPTIONAL
}

CellMeasuredResults ::=				SEQUENCE {
	cellIdentity						CellIdentity						OPTIONAL,
	-- dummy is not used in this version of the specification, it should
	-- not be sent and if received it should be ignored.
	dummy			SFN-SFN-ObsTimeDifference			OPTIONAL,
	cellSynchronisationInfo			CellSynchronisationInfo			OPTIONAL,
	modeSpecificInfo					CHOICE {
		fdd									SEQUENCE {
			primaryCPICH-Info					PrimaryCPICH-Info,
			cpich-Ec-N0							CPICH-Ec-N0					OPTIONAL,
			cpich-RSCP							CPICH-RSCP					OPTIONAL,
			pathloss							Pathloss					OPTIONAL
		},
		tdd									SEQUENCE {
			cellParametersID					CellParametersID,
			proposedTGSN						TGSN						OPTIONAL,
			primaryCCPCH-RSCP					PrimaryCCPCH-RSCP			OPTIONAL,
			pathloss							Pathloss					OPTIONAL,
			timeslotISCP-List					TimeslotISCP-List			OPTIONAL
		}
	}
}

CellMeasurementEventResults ::=		CHOICE {
	fdd									SEQUENCE (SIZE (1..maxCellMeas)) OF
											PrimaryCPICH-Info,
	tdd									SEQUENCE (SIZE (1..maxCellMeas)) OF
											PrimaryCCPCH-Info
}

CellReportingQuantities ::=			SEQUENCE {
	-- dummy is not used in this version of the specification, it should
	-- be ignored by the receiver
	dummy					SFN-SFN-OTD-Type,
	cellIdentity-reportingIndicator						BOOLEAN,
	cellSynchronisationInfoReportingIndicator			BOOLEAN,
	modeSpecificInfo					CHOICE {
		fdd									SEQUENCE {
			cpich-Ec-N0-reportingIndicator							BOOLEAN,
			cpich-RSCP-reportingIndicator							BOOLEAN,
			pathloss-reportingIndicator							BOOLEAN
		},
		tdd									SEQUENCE {
			timeslotISCP-reportingIndicator						BOOLEAN,
			proposedTGSN-ReportingRequired						BOOLEAN,
			primaryCCPCH-RSCP-reportingIndicator					BOOLEAN,
			pathloss-reportingIndicator							BOOLEAN
		}
	}
}

CellSelectReselectInfoSIB-11-12 ::=	SEQUENCE {
	q-Offset1S-N						Q-OffsetS-N							DEFAULT 0,
	q-Offset2S-N						Q-OffsetS-N							OPTIONAL,
	maxAllowedUL-TX-Power				MaxAllowedUL-TX-Power				OPTIONAL,
	hcs-NeighbouringCellInformation-RSCP		HCS-NeighbouringCellInformation-RSCP		OPTIONAL,
	modeSpecificInfo					CHOICE {
		fdd									SEQUENCE {
			q-QualMin							Q-QualMin					OPTIONAL,
			q-RxlevMin							Q-RxlevMin					OPTIONAL
		},
		tdd									SEQUENCE {
			q-RxlevMin							Q-RxlevMin					OPTIONAL
		},
		gsm									SEQUENCE {
			q-RxlevMin							Q-RxlevMin					OPTIONAL
		}
	}
}

CellSelectReselectInfoSIB-11-12-RSCP ::=	SEQUENCE {
	q-OffsetS-N						Q-OffsetS-N						DEFAULT 0,
	maxAllowedUL-TX-Power				MaxAllowedUL-TX-Power				OPTIONAL,
	modeSpecificInfo					CHOICE {
		fdd									SEQUENCE {
			q-QualMin							Q-QualMin					OPTIONAL,
			q-RxlevMin							Q-RxlevMin					OPTIONAL
		},
		tdd									SEQUENCE {
			q-RxlevMin							Q-RxlevMin					OPTIONAL
		},
		gsm									SEQUENCE {
			q-RxlevMin							Q-RxlevMin					OPTIONAL
		}
	}
}

CellSelectReselectInfoSIB-11-12-ECN0 ::=	SEQUENCE {
	q-Offset1S-N						Q-OffsetS-N						DEFAULT 0,
	q-Offset2S-N						Q-OffsetS-N						DEFAULT 0,
	maxAllowedUL-TX-Power				MaxAllowedUL-TX-Power				OPTIONAL,
	modeSpecificInfo					CHOICE {
		fdd									SEQUENCE {
			q-QualMin							Q-QualMin					OPTIONAL,
			q-RxlevMin							Q-RxlevMin					OPTIONAL
		},
		tdd									SEQUENCE {
			q-RxlevMin							Q-RxlevMin					OPTIONAL
		},
		gsm									SEQUENCE {
			q-RxlevMin							Q-RxlevMin					OPTIONAL
		}
	}
}

CellSelectReselectInfoSIB-11-12-HCS-RSCP ::=	SEQUENCE {
	q-OffsetS-N						Q-OffsetS-N						DEFAULT 0,
	maxAllowedUL-TX-Power				MaxAllowedUL-TX-Power				OPTIONAL,
	hcs-NeighbouringCellInformation-RSCP		HCS-NeighbouringCellInformation-RSCP		OPTIONAL,
	modeSpecificInfo					CHOICE {
		fdd									SEQUENCE {
			q-QualMin							Q-QualMin					OPTIONAL,
			q-RxlevMin							Q-RxlevMin					OPTIONAL
		},
		tdd									SEQUENCE {
			q-RxlevMin							Q-RxlevMin					OPTIONAL
		},
		gsm									SEQUENCE {
			q-RxlevMin							Q-RxlevMin					OPTIONAL
		}
	}
}

CellSelectReselectInfoSIB-11-12-HCS-ECN0 ::=	SEQUENCE {
	q-Offset1S-N						Q-OffsetS-N						DEFAULT 0,
	q-Offset2S-N						Q-OffsetS-N						DEFAULT 0,
	maxAllowedUL-TX-Power				MaxAllowedUL-TX-Power				OPTIONAL,
	hcs-NeighbouringCellInformation-ECN0		HCS-NeighbouringCellInformation-ECN0		OPTIONAL,
	modeSpecificInfo					CHOICE {
		fdd									SEQUENCE {
			q-QualMin							Q-QualMin					OPTIONAL,
			q-RxlevMin							Q-RxlevMin					OPTIONAL
		},
		tdd									SEQUENCE {
			q-RxlevMin							Q-RxlevMin					OPTIONAL
		},
		gsm									SEQUENCE {
			q-RxlevMin							Q-RxlevMin					OPTIONAL
		}
	}
}

CellsForInterFreqMeasList ::=		SEQUENCE (SIZE  (1..maxCellMeas)) OF
										InterFreqCellID
CellsForInterRATMeasList ::=			SEQUENCE (SIZE  (1..maxCellMeas)) OF
										InterRATCellID
CellsForIntraFreqMeasList ::=		SEQUENCE (SIZE  (1..maxCellMeas)) OF
										IntraFreqCellID

CellSynchronisationInfo ::=			SEQUENCE {
	modeSpecificInfo					CHOICE {
		fdd									SEQUENCE {
			countC-SFN-Frame-difference			CountC-SFN-Frame-difference		OPTIONAL,
			tm									INTEGER(0..38399)	
		},
		tdd									SEQUENCE {
			countC-SFN-Frame-difference			CountC-SFN-Frame-difference		OPTIONAL
		}
	}							
}

CellToReport ::=					SEQUENCE {
	bsicReported						BSICReported
}

CellToReportList ::=				SEQUENCE (SIZE (1..maxCellMeas)) OF
										CellToReport

CodePhaseSearchWindow ::=			ENUMERATED {
										w1023, w1, w2, w3, w4, w6, w8,
										w12, w16, w24, w32, w48, w64,
										w96, w128, w192 }

CountC-SFN-Frame-difference ::= SEQUENCE {
	-- Actual value countC-SFN-High = IE value * 256
	countC-SFN-High					INTEGER(0..15),
	off								INTEGER(0..255)
}

-- SPARE: CPICH-Ec-No, Max = 49
-- Values above Max are spare
CPICH-Ec-N0 ::=						INTEGER (0..63)

-- SPARE: CPICH- RSCP, Max = 91
-- Values above Max are spare
CPICH-RSCP ::=						INTEGER (0..127)


DeltaPRC ::=						INTEGER (-127..127)

-- Actual value DeltaRRC = IE value * 0.032
DeltaRRC ::=						INTEGER (-7..7)

DGPS-CorrectionSatInfo ::=			SEQUENCE {
	satID								SatID,
	iode								IODE,
	udre								UDRE,
	prc									PRC,
	rrc									RRC,
	-- dummy1 and dummy2 are not used in this version of the specification and should be ignored.
	dummy1							DeltaPRC,
	dummy2							DeltaRRC,
	-- dummy3 and dummy4 are not used in this version of the specification. They should not
	-- be sent and if received they should be ignored.
	dummy3							DeltaPRC			OPTIONAL,
	dummy4							DeltaRRC			OPTIONAL
}

DGPS-CorrectionSatInfoList ::=		SEQUENCE (SIZE (1..maxSat)) OF
										DGPS-CorrectionSatInfo

DiffCorrectionStatus ::=			ENUMERATED {
										udre-1-0, udre-0-75, udre-0-5, udre-0-3,
										udre-0-2, udre-0-1, noData, invalidData }

DL-TransportChannelBLER ::=			INTEGER (0..63)

DopplerUncertainty ::=				ENUMERATED {
										hz12-5, hz25, hz50, hz100, hz200,
										spare3, spare2, spare1 }

EllipsoidPoint ::=					SEQUENCE {	
	latitudeSign		ENUMERATED { north, south },
	latitude			INTEGER (0..8388607),
	longitude			INTEGER (-8388608..8388607)
}


EllipsoidPointAltitude ::=			SEQUENCE {
	latitudeSign		ENUMERATED { north, south },
	latitude			INTEGER (0..8388607),
	longitude			INTEGER (-8388608..8388607),
	altitudeDirection	ENUMERATED {height, depth},
	altitude			INTEGER (0..32767)
}


EllipsoidPointAltitudeEllipsoide ::=	SEQUENCE {
	latitudeSign			ENUMERATED { north, south },
	latitude				INTEGER (0..8388607),
	longitude				INTEGER (-8388608..8388607),
	altitudeDirection		ENUMERATED {height, depth},
	altitude				INTEGER (0..32767),
	uncertaintySemiMajor	INTEGER (0..127),
	uncertaintySemiMinor	INTEGER (0..127),
	-- Actual value orientationMajorAxis = IE value * 2
	orientationMajorAxis	INTEGER (0..89),
	uncertaintyAltitude		INTEGER (0..127),
	confidence				INTEGER (0..100)
}


EllipsoidPointUncertCircle ::=		SEQUENCE {
	latitudeSign			ENUMERATED { north, south },
	latitude				INTEGER (0..8388607),
	longitude				INTEGER (-8388608..8388607),
	uncertaintyCode			INTEGER (0..127)
}


EllipsoidPointUncertEllipse ::=		SEQUENCE {
	latitudeSign			ENUMERATED { north, south },
	latitude				INTEGER (0..8388607),
	longitude				INTEGER (-8388608..8388607),
	uncertaintySemiMajor	INTEGER (0..127),
	uncertaintySemiMinor	INTEGER (0..127),
	-- Actual value orientationMajorAxis = IE value * 2
	orientationMajorAxis	INTEGER (0..89),
	confidence				INTEGER (0..100)
}


EnvironmentCharacterisation ::=		ENUMERATED {
										possibleHeavyMultipathNLOS,
										lightMultipathLOS,
										notDefined,
										spare }

Event1a ::=							SEQUENCE {
	triggeringCondition					TriggeringCondition2,
	reportingRange						ReportingRange,
	forbiddenAffectCellList				ForbiddenAffectCellList				OPTIONAL,
	w									W,
	reportDeactivationThreshold			ReportDeactivationThreshold,
	reportingAmount						ReportingAmount,
	reportingInterval					ReportingInterval
}

Event1b ::=							SEQUENCE {
	triggeringCondition					TriggeringCondition1,
	reportingRange						ReportingRange,
	forbiddenAffectCellList				ForbiddenAffectCellList				OPTIONAL,
	w									W
}

Event1c ::=							SEQUENCE {
	replacementActivationThreshold		ReplacementActivationThreshold,
	reportingAmount						ReportingAmount,
	reportingInterval					ReportingInterval
}

Event1e ::=						SEQUENCE {
	triggeringCondition					TriggeringCondition2,
	thresholdUsedFrequency				ThresholdUsedFrequency
}

Event1f ::=						SEQUENCE {
	triggeringCondition					TriggeringCondition1,
	thresholdUsedFrequency				ThresholdUsedFrequency
}

Event2a ::=							SEQUENCE {
	-- dummy is not used in this version of the specification and should be ignored
	dummy				Threshold,
	usedFreqW							W,
	hysteresis							HysteresisInterFreq,
	timeToTrigger						TimeToTrigger,
	reportingCellStatus					ReportingCellStatus					OPTIONAL,
	nonUsedFreqParameterList			NonUsedFreqParameterList			OPTIONAL
}

Event2b ::=							SEQUENCE {
	usedFreqThreshold					Threshold,
	usedFreqW							W,
	hysteresis							HysteresisInterFreq,
	timeToTrigger						TimeToTrigger,
	reportingCellStatus					ReportingCellStatus					OPTIONAL,
	nonUsedFreqParameterList			NonUsedFreqParameterList			OPTIONAL
}

Event2c ::=							SEQUENCE {
	hysteresis							HysteresisInterFreq,
	timeToTrigger						TimeToTrigger,
	reportingCellStatus					ReportingCellStatus					OPTIONAL,
	nonUsedFreqParameterList			NonUsedFreqParameterList			OPTIONAL
}

Event2d ::=							SEQUENCE {
	usedFreqThreshold					Threshold,
	usedFreqW							W,
	hysteresis							HysteresisInterFreq,
	timeToTrigger						TimeToTrigger,
	reportingCellStatus					ReportingCellStatus					OPTIONAL
}

Event2e ::=							SEQUENCE {
	hysteresis							HysteresisInterFreq,
	timeToTrigger						TimeToTrigger,
	reportingCellStatus					ReportingCellStatus					OPTIONAL,
	nonUsedFreqParameterList			NonUsedFreqParameterList			OPTIONAL
}

Event2f ::=							SEQUENCE {
	usedFreqThreshold					Threshold,
	usedFreqW							W,
	hysteresis							HysteresisInterFreq,
	timeToTrigger						TimeToTrigger,
	reportingCellStatus					ReportingCellStatus					OPTIONAL
}	

Event3a ::=							SEQUENCE {
	thresholdOwnSystem					Threshold,
	w									W,
	thresholdOtherSystem				Threshold,
	hysteresis							Hysteresis,
	timeToTrigger						TimeToTrigger,
	reportingCellStatus					ReportingCellStatus					OPTIONAL
}	

Event3b ::=							SEQUENCE {
	thresholdOtherSystem				Threshold,
	hysteresis							Hysteresis,
	timeToTrigger						TimeToTrigger,
	reportingCellStatus					ReportingCellStatus					OPTIONAL
	
}	

Event3c ::=							SEQUENCE {
	thresholdOtherSystem				Threshold,
	hysteresis							Hysteresis,
	timeToTrigger						TimeToTrigger,
	reportingCellStatus					ReportingCellStatus					OPTIONAL
}	

Event3d ::=							SEQUENCE {
	hysteresis							Hysteresis,
	timeToTrigger						TimeToTrigger,
	reportingCellStatus					ReportingCellStatus					OPTIONAL
}	

EventIDInterFreq ::=				ENUMERATED {
										e2a, e2b, e2c, e2d, e2e, e2f, spare2, spare1 }

EventIDInterRAT ::=					ENUMERATED {
										e3a, e3b, e3c, e3d }

EventIDIntraFreq ::=				ENUMERATED {
										e1a, e1b, e1c, e1d, e1e,
										e1f, e1g, e1h, e1i, spare7,
										spare6, spare5, spare4, spare3, spare2,
										spare1 }

EventResults ::=					CHOICE {
	intraFreqEventResults				IntraFreqEventResults,
	interFreqEventResults				InterFreqEventResults,
	interRATEventResults				InterRATEventResults,
	trafficVolumeEventResults			TrafficVolumeEventResults,
	qualityEventResults					QualityEventResults,
	ue-InternalEventResults				UE-InternalEventResults,
	ue-positioning-MeasurementEventResults			UE-Positioning-MeasurementEventResults,
	spare								NULL
}

ExtraDopplerInfo ::=				SEQUENCE {
	-- Actual value doppler1stOrder = IE value * 0.023
	doppler1stOrder						INTEGER (-42..21),
	dopplerUncertainty					DopplerUncertainty
}

FACH-MeasurementOccasionInfo ::=	SEQUENCE {
	fACH-meas-occasion-coeff			INTEGER (1..12)						OPTIONAL,
	inter-freq-FDD-meas-ind				BOOLEAN,
	inter-freq-TDD-meas-ind				BOOLEAN,
	inter-RAT-meas-ind					SEQUENCE (SIZE (1..maxOtherRAT)) OF
											RAT-Type						OPTIONAL
}

FilterCoefficient ::=				ENUMERATED {
										fc0, fc1, fc2, fc3, fc4, fc5,
										fc6, fc7, fc8, fc9, fc11, fc13,
										fc15, fc17, fc19, spare1 }

-- Actual value FineSFN-SFN = IE value * 0.0625
FineSFN-SFN ::=						INTEGER (0..15)

ForbiddenAffectCell ::=				CHOICE {
	fdd									PrimaryCPICH-Info,
	tdd									PrimaryCCPCH-Info
}

ForbiddenAffectCellList ::=			SEQUENCE (SIZE (1..maxCellMeas)) OF
										ForbiddenAffectCell

FreqQualityEstimateQuantity-FDD ::= ENUMERATED {
										cpich-Ec-N0,
										cpich-RSCP }

FreqQualityEstimateQuantity-TDD ::= ENUMERATED {
										primaryCCPCH-RSCP }

GPS-MeasurementParam ::=			SEQUENCE {
	satelliteID							INTEGER (0..63),
	c-N0								INTEGER (0..63),
	doppler								INTEGER (-32768..32768),
	wholeGPS-Chips						INTEGER (0..1022),
	fractionalGPS-Chips					INTEGER (0..1023),
	multipathIndicator					MultipathIndicator,
	pseudorangeRMS-Error				INTEGER (0..63)
}

GPS-MeasurementParamList ::=		SEQUENCE (SIZE (1..maxSat)) OF
										GPS-MeasurementParam

GSM-CarrierRSSI ::=					BIT STRING (SIZE (6))


GSM-MeasuredResults ::=			SEQUENCE {
	gsm-CarrierRSSI						GSM-CarrierRSSI						OPTIONAL,
	-- dummy is not used in this version of the specification, it should
	-- not be sent and if received it should be ignored.
	dummy								INTEGER (46..173)					OPTIONAL,
	bsicReported						BSICReported,
	observedTimeDifferenceToGSM			ObservedTimeDifferenceToGSM			OPTIONAL
}

GSM-MeasuredResultsList ::=			SEQUENCE (SIZE (1..maxReportedGSMCells)) OF
										GSM-MeasuredResults	

GPS-TOW-1msec ::=					INTEGER (0..604799999)

GPS-TOW-Assist ::=					SEQUENCE {
	satID								SatID,
	tlm-Message							BIT STRING (SIZE (14)),
	tlm-Reserved						BIT STRING (SIZE (2)),
	alert								BOOLEAN,
	antiSpoof							BOOLEAN
}

GPS-TOW-AssistList ::=				SEQUENCE (SIZE (1..maxSat)) OF
										GPS-TOW-Assist

HCS-CellReselectInformation-RSCP ::=		SEQUENCE {
	-- TABULAR: The default value for penaltyTime is "notUsed"
	-- Temporary offset is nested inside PenaltyTime
	penaltyTime									PenaltyTime-RSCP
}

HCS-CellReselectInformation-ECN0 ::=		SEQUENCE {
	-- TABULAR: The default value for penaltyTime is "notUsed"
	-- Temporary offset is nested inside PenaltyTime
	penaltyTime							PenaltyTime-ECN0
}

HCS-NeighbouringCellInformation-RSCP ::= SEQUENCE {
	hcs-PRIO							HCS-PRIO							DEFAULT 0,
	q-HCS								Q-HCS								DEFAULT 0,
	hcs-CellReselectInformation			HCS-CellReselectInformation-RSCP
}

HCS-NeighbouringCellInformation-ECN0 ::= SEQUENCE {
	hcs-PRIO							HCS-PRIO							DEFAULT 0,
	q-HCS								Q-HCS								DEFAULT 0,
	hcs-CellReselectInformation			HCS-CellReselectInformation-ECN0
}

HCS-PRIO ::=						INTEGER (0..7)

HCS-ServingCellInformation ::=		SEQUENCE {
	hcs-PRIO							HCS-PRIO							DEFAULT 0,
	q-HCS								Q-HCS								DEFAULT 0,
	t-CR-Max							T-CRMax								OPTIONAL
}

-- Actual value Hysteresis = IE value * 0.5
Hysteresis ::=						INTEGER (0..15)

-- Actual value HysteresisInterFreq = IE value * 0.5
HysteresisInterFreq ::=				INTEGER (0..29)

InterFreqCell ::=					SEQUENCE {
	frequencyInfo						FrequencyInfo,
	nonFreqRelatedEventResults			CellMeasurementEventResults
}

InterFreqCellID ::=					INTEGER (0..maxCellMeas-1)

InterFreqCellInfoList ::=			SEQUENCE {
	removedInterFreqCellList			RemovedInterFreqCellList			OPTIONAL,
	newInterFreqCellList				NewInterFreqCellList				OPTIONAL,
	cellsForInterFreqMeasList			CellsForInterFreqMeasList			OPTIONAL
}

InterFreqCellInfoSI-List-RSCP ::=		SEQUENCE {
	removedInterFreqCellList			RemovedInterFreqCellList			OPTIONAL,
	newInterFreqCellList				NewInterFreqCellSI-List-RSCP		OPTIONAL
}

InterFreqCellInfoSI-List-ECN0 ::=		SEQUENCE {
	removedInterFreqCellList			RemovedInterFreqCellList			OPTIONAL,
	newInterFreqCellList				NewInterFreqCellSI-List-ECN0		OPTIONAL
}

InterFreqCellInfoSI-List-HCS-RSCP ::=		SEQUENCE {
	removedInterFreqCellList			RemovedInterFreqCellList			OPTIONAL,
	newInterFreqCellList				NewInterFreqCellSI-List-HCS-RSCP	OPTIONAL
}
InterFreqCellInfoSI-List-HCS-ECN0 ::=		SEQUENCE {
	removedInterFreqCellList			RemovedInterFreqCellList			OPTIONAL,
	newInterFreqCellList				NewInterFreqCellSI-List-HCS-ECN0	OPTIONAL
}

InterFreqCellList ::=				SEQUENCE (SIZE (1..maxFreq)) OF
										InterFreqCell

InterFreqCellMeasuredResultsList ::= SEQUENCE (SIZE (1..maxCellMeas)) OF
										CellMeasuredResults

InterFreqEvent ::=					CHOICE {
	event2a								Event2a,
	event2b								Event2b,
	event2c								Event2c,
	event2d								Event2d,
	event2e								Event2e,
	event2f								Event2f
}

InterFreqEventList ::=				SEQUENCE (SIZE (1..maxMeasEvent)) OF
										InterFreqEvent


InterFreqEventResults ::=			SEQUENCE {
	eventID								EventIDInterFreq,
	interFreqCellList					InterFreqCellList					OPTIONAL
}


InterFreqMeasQuantity ::=			SEQUENCE {
	reportingCriteria					CHOICE {
		intraFreqReportingCriteria			SEQUENCE {
			intraFreqMeasQuantity				IntraFreqMeasQuantity
		},
		interFreqReportingCriteria			SEQUENCE {
			filterCoefficient					FilterCoefficient			DEFAULT fc0,
			modeSpecificInfo					CHOICE {
				fdd									SEQUENCE {
					freqQualityEstimateQuantity-FDD		FreqQualityEstimateQuantity-FDD
				},
				tdd									SEQUENCE {
					freqQualityEstimateQuantity-TDD		FreqQualityEstimateQuantity-TDD
				}
			}
		}
	}
}

InterFreqMeasuredResults ::=		SEQUENCE {
	frequencyInfo						FrequencyInfo						OPTIONAL,
	utra-CarrierRSSI					UTRA-CarrierRSSI					OPTIONAL,
	interFreqCellMeasuredResultsList	InterFreqCellMeasuredResultsList	OPTIONAL
}

InterFreqMeasuredResultsList ::=	SEQUENCE (SIZE (1..maxFreq)) OF
										InterFreqMeasuredResults


InterFreqMeasurementSysInfo-RSCP ::=	SEQUENCE {
	interFreqCellInfoSI-List				InterFreqCellInfoSI-List-RSCP		OPTIONAL
}

InterFreqMeasurementSysInfo-ECN0 ::=		SEQUENCE {
	interFreqCellInfoSI-List			InterFreqCellInfoSI-List-ECN0		OPTIONAL
}

InterFreqMeasurementSysInfo-HCS-RSCP ::=		SEQUENCE {
	interFreqCellInfoSI-List			InterFreqCellInfoSI-List-HCS-RSCP	OPTIONAL
}

InterFreqMeasurementSysInfo-HCS-ECN0 ::=		SEQUENCE {
	interFreqCellInfoSI-List			InterFreqCellInfoSI-List-HCS-ECN0	OPTIONAL
}

InterFreqReportCriteria ::=			CHOICE {
	intraFreqReportingCriteria			IntraFreqReportingCriteria,
	interFreqReportingCriteria			InterFreqReportingCriteria,
	periodicalReportingCriteria			PeriodicalWithReportingCellStatus,
	noReporting							ReportingCellStatusOpt
}

InterFreqReportingCriteria ::=		SEQUENCE {
	interFreqEventList					InterFreqEventList					OPTIONAL
}

InterFreqReportingQuantity ::=		SEQUENCE {
	utra-Carrier-RSSI					BOOLEAN,
	frequencyQualityEstimate			BOOLEAN,
	nonFreqRelatedQuantities			CellReportingQuantities
}

InterFrequencyMeasurement ::=		SEQUENCE {
	interFreqCellInfoList				InterFreqCellInfoList,
	interFreqMeasQuantity				InterFreqMeasQuantity				OPTIONAL,
	interFreqReportingQuantity			InterFreqReportingQuantity			OPTIONAL,
	measurementValidity					MeasurementValidity					OPTIONAL,
	interFreqSetUpdate					UE-AutonomousUpdateMode				OPTIONAL,
	reportCriteria						InterFreqReportCriteria
}

InterRAT-TargetCellDescription::=	SEQUENCE {
	technologySpecificInfo				CHOICE {
		gsm									SEQUENCE {
			bsic								BSIC,
			frequency-band						Frequency-Band,
			bcch-ARFCN							BCCH-ARFCN,
			ncMode								NC-Mode				OPTIONAL
		},
		is-2000								NULL,
		spare2								NULL,
		spare1								NULL
	}
}

InterRATCellID ::=				INTEGER (0..maxCellMeas-1)

InterRATCellInfoList ::=			SEQUENCE {
	removedInterRATCellList			RemovedInterRATCellList,
	-- NOTE: Future revisions of dedicated messages including IE newInterRATCellList
	-- should use a corrected version of this IE
	newInterRATCellList				NewInterRATCellList,
	cellsForInterRATMeasList			CellsForInterRATMeasList			OPTIONAL
}

InterRATCellInfoList-B ::=			SEQUENCE {
	removedInterRATCellList			RemovedInterRATCellList,
	-- NOTE: IE newInterRATCellList should be optional.  However, system information
	-- does not support message versions.  Hence, this can not be corrected
	newInterRATCellList				NewInterRATCellList-B
}

InterRATCellIndividualOffset ::=			INTEGER (-50..50)

InterRATEvent ::=				CHOICE {
	event3a								Event3a,
	event3b								Event3b,
	event3c								Event3c,
	event3d								Event3d
}

InterRATEventList ::=			SEQUENCE (SIZE (1..maxMeasEvent)) OF
										InterRATEvent

InterRATEventResults ::=			SEQUENCE {
	eventID								EventIDInterRAT,
	cellToReportList					CellToReportList
}

InterRATInfo ::=					ENUMERATED {
										gsm }

InterRATMeasQuantity ::=				SEQUENCE {
	measQuantityUTRAN-QualityEstimate		IntraFreqMeasQuantity			OPTIONAL,
	ratSpecificInfo						CHOICE {
		gsm										SEQUENCE {
			measurementQuantity						MeasurementQuantityGSM,
			filterCoefficient						FilterCoefficient		DEFAULT fc0,
			bsic-VerificationRequired				BSIC-VerificationRequired
		},
		is-2000									SEQUENCE {
			tadd-EcIo								INTEGER (0..63),
			tcomp-EcIo								INTEGER (0..15),
			softSlope								INTEGER (0..63)			OPTIONAL,
			addIntercept							INTEGER (0..63)			OPTIONAL
		}
	}	
}

InterRATMeasuredResults ::=		CHOICE {
	gsm									GSM-MeasuredResultsList,
	spare								NULL
}

InterRATMeasuredResultsList ::= SEQUENCE (SIZE (1..maxOtherRAT-16)) OF
										InterRATMeasuredResults

InterRATMeasurement ::=			SEQUENCE {
	interRATCellInfoList				InterRATCellInfoList				OPTIONAL,
	interRATMeasQuantity				InterRATMeasQuantity				OPTIONAL,
	interRATReportingQuantity			InterRATReportingQuantity		OPTIONAL,
	reportCriteria						InterRATReportCriteria
}

InterRATMeasurementSysInfo ::=	SEQUENCE {
	interRATCellInfoList				InterRATCellInfoList				OPTIONAL
}

InterRATMeasurementSysInfo-B ::=	SEQUENCE {
	interRATCellInfoList				InterRATCellInfoList-B			OPTIONAL
}

InterRATReportCriteria ::=		CHOICE {
	interRATReportingCriteria			InterRATReportingCriteria,
	periodicalReportingCriteria			PeriodicalWithReportingCellStatus,
	noReporting							ReportingCellStatusOpt
}			

InterRATReportingCriteria ::=	SEQUENCE {
	interRATEventList				InterRATEventList				OPTIONAL
}

InterRATReportingQuantity ::=	SEQUENCE {
	utran-EstimatedQuality				BOOLEAN,
	ratSpecificInfo					CHOICE {
		gsm									SEQUENCE {
			dummy								BOOLEAN,
			observedTimeDifferenceGSM			BOOLEAN,
			gsm-Carrier-RSSI					BOOLEAN
		}
	}
}

IntraFreqCellID ::=					INTEGER (0..maxCellMeas-1)

IntraFreqCellInfoList ::=			SEQUENCE {
	removedIntraFreqCellList			RemovedIntraFreqCellList			OPTIONAL,
	newIntraFreqCellList				NewIntraFreqCellList				OPTIONAL,
	cellsForIntraFreqMeasList			CellsForIntraFreqMeasList			OPTIONAL
}

IntraFreqCellInfoSI-List-RSCP ::=	SEQUENCE {
	removedIntraFreqCellList			RemovedIntraFreqCellList			OPTIONAL,
	newIntraFreqCellList				NewIntraFreqCellSI-List-RSCP
}

IntraFreqCellInfoSI-List-ECN0 ::=		SEQUENCE {
	removedIntraFreqCellList			RemovedIntraFreqCellList			OPTIONAL,
	newIntraFreqCellList				NewIntraFreqCellSI-List-ECN0
}

IntraFreqCellInfoSI-List-HCS-RSCP ::=		SEQUENCE {
	removedIntraFreqCellList			RemovedIntraFreqCellList			OPTIONAL,
	newIntraFreqCellList				NewIntraFreqCellSI-List-HCS-RSCP
}

IntraFreqCellInfoSI-List-HCS-ECN0 ::=		SEQUENCE {
	removedIntraFreqCellList			RemovedIntraFreqCellList			OPTIONAL,
	newIntraFreqCellList				NewIntraFreqCellSI-List-HCS-ECN0
}

IntraFreqEvent ::=					CHOICE {
	e1a									Event1a,
	e1b									Event1b,
	e1c									Event1c,
	e1d									NULL,
	e1e									Event1e,
	e1f									Event1f,
	e1g									NULL,
	e1h									ThresholdUsedFrequency,
	e1i									ThresholdUsedFrequency
}

IntraFreqEventCriteria ::=			SEQUENCE {
	event								IntraFreqEvent,
	hysteresis							Hysteresis,
	timeToTrigger						TimeToTrigger,
	reportingCellStatus					ReportingCellStatus					OPTIONAL
}

IntraFreqEventCriteriaList ::=		SEQUENCE (SIZE (1..maxMeasEvent)) OF
										IntraFreqEventCriteria

IntraFreqEventResults ::=			SEQUENCE {
	eventID								EventIDIntraFreq,
	cellMeasurementEventResults			CellMeasurementEventResults
}

IntraFreqMeasQuantity ::=			SEQUENCE {
	filterCoefficient					FilterCoefficient					DEFAULT fc0,
	modeSpecificInfo					CHOICE {
		fdd								SEQUENCE {
			intraFreqMeasQuantity-FDD		IntraFreqMeasQuantity-FDD
		},
		tdd								SEQUENCE {
			intraFreqMeasQuantity-TDDList	IntraFreqMeasQuantity-TDDList
		}
	}
}

-- If IntraFreqMeasQuantity-FDD is used in InterRATMeasQuantity, then only
-- cpich-Ec-N0 and cpich-RSCP are allowed.
-- dummy is not used in this version of the specification, it should
-- not be sent and if received it should be ignored.
IntraFreqMeasQuantity-FDD ::=		ENUMERATED {
										cpich-Ec-N0,
										cpich-RSCP,
										pathloss,
										dummy }

-- dummy is not used in this version of the specification, it should
-- not be sent and if received it should be ignored.
IntraFreqMeasQuantity-TDD ::=		ENUMERATED {
										primaryCCPCH-RSCP,
										pathloss,
										timeslotISCP,
										dummy }

IntraFreqMeasQuantity-TDDList ::=	SEQUENCE (SIZE (1..4)) OF
										IntraFreqMeasQuantity-TDD

IntraFreqMeasuredResultsList ::=	SEQUENCE (SIZE (1..maxCellMeas)) OF
										CellMeasuredResults

IntraFreqMeasurementSysInfo-RSCP ::=	SEQUENCE {
	intraFreqMeasurementID				MeasurementIdentity			DEFAULT 1,
	intraFreqCellInfoSI-List			IntraFreqCellInfoSI-List-RSCP		OPTIONAL,
	intraFreqMeasQuantity				IntraFreqMeasQuantity				OPTIONAL,
	intraFreqReportingQuantityForRACH	IntraFreqReportingQuantityForRACH	OPTIONAL,
	maxReportedCellsOnRACH				MaxReportedCellsOnRACH				OPTIONAL,
	reportingInfoForCellDCH				ReportingInfoForCellDCH				OPTIONAL
}

IntraFreqMeasurementSysInfo-ECN0 ::=		SEQUENCE {
	intraFreqMeasurementID				MeasurementIdentity			DEFAULT 1,
	intraFreqCellInfoSI-List			IntraFreqCellInfoSI-List-ECN0		OPTIONAL,
	intraFreqMeasQuantity				IntraFreqMeasQuantity				OPTIONAL,
	intraFreqReportingQuantityForRACH	IntraFreqReportingQuantityForRACH	OPTIONAL,
	maxReportedCellsOnRACH				MaxReportedCellsOnRACH				OPTIONAL,
	reportingInfoForCellDCH				ReportingInfoForCellDCH				OPTIONAL
}

IntraFreqMeasurementSysInfo-HCS-RSCP ::=	SEQUENCE {
	intraFreqMeasurementID				MeasurementIdentity			DEFAULT 1,
	intraFreqCellInfoSI-List			IntraFreqCellInfoSI-List-HCS-RSCP	OPTIONAL,
	intraFreqMeasQuantity				IntraFreqMeasQuantity				OPTIONAL,
	intraFreqReportingQuantityForRACH	IntraFreqReportingQuantityForRACH	OPTIONAL,
	maxReportedCellsOnRACH				MaxReportedCellsOnRACH				OPTIONAL,
	reportingInfoForCellDCH				ReportingInfoForCellDCH				OPTIONAL
}

IntraFreqMeasurementSysInfo-HCS-ECN0 ::=	SEQUENCE {
	intraFreqMeasurementID				MeasurementIdentity			DEFAULT 1,
	intraFreqCellInfoSI-List			IntraFreqCellInfoSI-List-HCS-ECN0	OPTIONAL,
	intraFreqMeasQuantity				IntraFreqMeasQuantity				OPTIONAL,
	intraFreqReportingQuantityForRACH	IntraFreqReportingQuantityForRACH	OPTIONAL,
	maxReportedCellsOnRACH				MaxReportedCellsOnRACH				OPTIONAL,
	reportingInfoForCellDCH				ReportingInfoForCellDCH				OPTIONAL
}

IntraFreqReportCriteria ::=			CHOICE {
	intraFreqReportingCriteria			IntraFreqReportingCriteria,
	periodicalReportingCriteria			PeriodicalWithReportingCellStatus,
	noReporting							ReportingCellStatusOpt
}

IntraFreqReportingCriteria ::=		SEQUENCE {
	eventCriteriaList					IntraFreqEventCriteriaList		OPTIONAL
}

IntraFreqReportingQuantity ::=		SEQUENCE {
	activeSetReportingQuantities		CellReportingQuantities,
	monitoredSetReportingQuantities		CellReportingQuantities,
	detectedSetReportingQuantities		CellReportingQuantities				OPTIONAL
}

IntraFreqReportingQuantityForRACH ::= SEQUENCE {
	sfn-SFN-OTD-Type					SFN-SFN-OTD-Type,
	modeSpecificInfo					CHOICE {
		fdd									SEQUENCE {
			intraFreqRepQuantityRACH-FDD		IntraFreqRepQuantityRACH-FDD
		},
		tdd									SEQUENCE {
			intraFreqRepQuantityRACH-TDDList	IntraFreqRepQuantityRACH-TDDList
		}
	}
}

IntraFreqRepQuantityRACH-FDD ::=	ENUMERATED {
										cpich-EcN0, cpich-RSCP,
										pathloss, noReport }

IntraFreqRepQuantityRACH-TDD ::=	ENUMERATED {
										timeslotISCP,
										primaryCCPCH-RSCP,
										noReport }

IntraFreqRepQuantityRACH-TDDList ::= SEQUENCE (SIZE (1..2)) OF
										IntraFreqRepQuantityRACH-TDD

IntraFrequencyMeasurement ::=		SEQUENCE {
	intraFreqCellInfoList				IntraFreqCellInfoList				OPTIONAL,
	intraFreqMeasQuantity				IntraFreqMeasQuantity				OPTIONAL,
	intraFreqReportingQuantity			IntraFreqReportingQuantity			OPTIONAL,
	measurementValidity					MeasurementValidity					OPTIONAL,
	reportCriteria						IntraFreqReportCriteria				OPTIONAL
}

IODE ::=							INTEGER (0..255)

IP-Length ::=						ENUMERATED {
										ipl5, ipl10 }

IP-Spacing ::=						ENUMERATED {
										e5, e7, e10, e15, e20,
										e30, e40, e50 }

IS-2000SpecificMeasInfo ::=			ENUMERATED {
										frequency, timeslot, colourcode,
										outputpower, pn-Offset }

MaxNumberOfReportingCellsType1 ::=	ENUMERATED {
										e1, e2, e3, e4, e5, e6}

MaxNumberOfReportingCellsType2 ::=	ENUMERATED {
										e1, e2, e3, e4, e5, e6, e7, e8, e9, e10, e11, e12}

MaxNumberOfReportingCellsType3 ::=	ENUMERATED {
										viactCellsPlus1,
										viactCellsPlus2,
										viactCellsPlus3,
										viactCellsPlus4,
										viactCellsPlus5,
										viactCellsPlus6 }

MaxReportedCellsOnRACH ::=			ENUMERATED {
										noReport,
										currentCell,
										currentAnd-1-BestNeighbour,
										currentAnd-2-BestNeighbour,
										currentAnd-3-BestNeighbour,
										currentAnd-4-BestNeighbour,
										currentAnd-5-BestNeighbour,
										currentAnd-6-BestNeighbour }

MeasuredResults ::=					CHOICE {
	intraFreqMeasuredResultsList		IntraFreqMeasuredResultsList,
	interFreqMeasuredResultsList		InterFreqMeasuredResultsList,
	interRATMeasuredResultsList		InterRATMeasuredResultsList,
	trafficVolumeMeasuredResultsList	TrafficVolumeMeasuredResultsList,
	qualityMeasuredResults				QualityMeasuredResults,
	ue-InternalMeasuredResults			UE-InternalMeasuredResults,
	ue-positioning-MeasuredResults					UE-Positioning-MeasuredResults,
	spare								NULL
}

MeasuredResults-v390ext ::=					SEQUENCE {
	ue-positioning-MeasuredResults-v390ext					UE-Positioning-MeasuredResults-v390ext
}

MeasuredResultsList ::=				SEQUENCE (SIZE (1..maxAdditionalMeas)) OF
										MeasuredResults

MeasuredResultsOnRACH ::=			SEQUENCE {
	currentCell						SEQUENCE {
		modeSpecificInfo					CHOICE {
			fdd									SEQUENCE {
				measurementQuantity					CHOICE {
					cpich-Ec-N0							CPICH-Ec-N0,
					cpich-RSCP							CPICH-RSCP,
					pathloss							Pathloss,
					spare								NULL
				}
			},
			tdd									SEQUENCE {
				timeslotISCP						TimeslotISCP-List		OPTIONAL,
				primaryCCPCH-RSCP					PrimaryCCPCH-RSCP		OPTIONAL
			}
		}
	},
	monitoredCells						MonitoredCellRACH-List				OPTIONAL
}

MeasurementCommand ::=				CHOICE {
	setup								MeasurementType,
	modify								SEQUENCE {
		measurementType						MeasurementType					OPTIONAL
	},
	release								NULL
}

MeasurementControlSysInfo ::=		SEQUENCE {
	use-of-HCS							CHOICE	{
		hcs-not-used					SEQUENCE	{
			cellSelectQualityMeasure	CHOICE	{
				cpich-RSCP				SEQUENCE	{
					intraFreqMeasurementSysInfo			IntraFreqMeasurementSysInfo-RSCP	OPTIONAL,
					interFreqMeasurementSysInfo			InterFreqMeasurementSysInfo-RSCP	OPTIONAL
				},
				cpich-Ec-N0				SEQUENCE	{
					intraFreqMeasurementSysInfo			IntraFreqMeasurementSysInfo-ECN0		OPTIONAL,
					interFreqMeasurementSysInfo			InterFreqMeasurementSysInfo-ECN0	OPTIONAL
				}
			},
			interRATMeasurementSysInfo		InterRATMeasurementSysInfo-B		OPTIONAL
		},
		hcs-used						SEQUENCE	{
			cellSelectQualityMeasure	CHOICE	{
				cpich-RSCP				SEQUENCE	{
					intraFreqMeasurementSysInfo			IntraFreqMeasurementSysInfo-HCS-RSCP			OPTIONAL,
					interFreqMeasurementSysInfo			InterFreqMeasurementSysInfo-HCS-RSCP			OPTIONAL
				},
				cpich-Ec-N0				SEQUENCE	{
					intraFreqMeasurementSysInfo			IntraFreqMeasurementSysInfo-HCS-ECN0			OPTIONAL,
					interFreqMeasurementSysInfo			InterFreqMeasurementSysInfo-HCS-ECN0			OPTIONAL				}
			},
			interRATMeasurementSysInfo		InterRATMeasurementSysInfo		OPTIONAL
		}
	},

	trafficVolumeMeasSysInfo			TrafficVolumeMeasSysInfo			OPTIONAL,
	-- dummy is not used in this version of specification and it shall be ignored by the UE.
	dummy								UE-InternalMeasurementSysInfo		OPTIONAL
}

MeasurementIdentity ::=		INTEGER (1..16)

MeasurementQuantityGSM ::=			ENUMERATED {
										gsm-CarrierRSSI,
										dummy }

MeasurementReportingMode ::=		SEQUENCE {
	measurementReportTransferMode		TransferMode,
	periodicalOrEventTrigger			PeriodicalOrEventTrigger
}	

MeasurementType ::=					CHOICE {
	intraFrequencyMeasurement			IntraFrequencyMeasurement,
	interFrequencyMeasurement			InterFrequencyMeasurement,
	interRATMeasurement				InterRATMeasurement,
	ue-positioning-Measurement						UE-Positioning-Measurement,
	trafficVolumeMeasurement			TrafficVolumeMeasurement,
	qualityMeasurement					QualityMeasurement,
	ue-InternalMeasurement				UE-InternalMeasurement
}

MeasurementValidity ::=				SEQUENCE {
	ue-State							ENUMERATED {
											cell-DCH, all-But-Cell-DCH, all-States }
}

MonitoredCellRACH-List ::=			SEQUENCE (SIZE (1..8)) OF
										MonitoredCellRACH-Result

MonitoredCellRACH-Result ::=		SEQUENCE {
	sfn-SFN-ObsTimeDifference			SFN-SFN-ObsTimeDifference			OPTIONAL,
	modeSpecificInfo					CHOICE {
		fdd									SEQUENCE {
			primaryCPICH-Info					PrimaryCPICH-Info,
			measurementQuantity					CHOICE {
				cpich-Ec-N0							CPICH-Ec-N0,
				cpich-RSCP							CPICH-RSCP,
				pathloss							Pathloss,
				spare								NULL
			}																OPTIONAL
		},
		tdd									SEQUENCE {
			cellParametersID					CellParametersID,
			primaryCCPCH-RSCP					PrimaryCCPCH-RSCP
		}
	}
}

MultipathIndicator ::=				ENUMERATED {
										nm,
										low,
										medium,
										high }

N-CR-T-CRMaxHyst ::=				SEQUENCE {
	n-CR								INTEGER (1..16)						DEFAULT 8,
	t-CRMaxHyst							T-CRMaxHyst
}

NavigationModelSatInfo ::=			SEQUENCE {
	satID								SatID,
	satelliteStatus						SatelliteStatus,
	ephemerisParameter					EphemerisParameter		OPTIONAL
}

NavigationModelSatInfoList ::=		SEQUENCE (SIZE (1..maxSat)) OF
										NavigationModelSatInfo

EphemerisParameter ::=				SEQUENCE {
	codeOnL2							BIT STRING (SIZE (2)),
	uraIndex							BIT STRING (SIZE (4)),
	satHealth							BIT STRING (SIZE (6)),
	iodc								BIT STRING (SIZE (10)),
	l2Pflag								BIT STRING (SIZE (1)),
	sf1Revd								SubFrame1Reserved,
	t-GD								BIT STRING (SIZE (8)),
	t-oc								BIT STRING (SIZE (16)),
	af2									BIT STRING (SIZE (8)),
	af1									BIT STRING (SIZE (16)),
	af0									BIT STRING (SIZE (22)),
	c-rs								BIT STRING (SIZE (16)),
	delta-n								BIT STRING (SIZE (16)),
	m0									BIT STRING (SIZE (32)),
	c-uc								BIT STRING (SIZE (16)),
	e									BIT STRING (SIZE (32)),
	c-us								BIT STRING (SIZE (16)),
	a-Sqrt								BIT STRING (SIZE (32)),
	t-oe								BIT STRING (SIZE (16)),
	fitInterval							BIT STRING (SIZE (1)),
	aodo								BIT STRING (SIZE (5)),
	c-ic								BIT STRING (SIZE (16)),
	omega0								BIT STRING (SIZE (32)),
	c-is								BIT STRING (SIZE (16)),
	i0									BIT STRING (SIZE (32)),
	c-rc								BIT STRING (SIZE (16)),
	omega								BIT STRING (SIZE (32)),
	omegaDot							BIT STRING (SIZE (24)),
	iDot								BIT STRING (SIZE (14))
}
NC-Mode::=							BIT STRING (SIZE (3))

Neighbour ::=						SEQUENCE {
	modeSpecificInfo				CHOICE {
		fdd								SEQUENCE {
			neighbourIdentity					PrimaryCPICH-Info					OPTIONAL,
			uE-RX-TX-TimeDifferenceType2Info	UE-RX-TX-TimeDifferenceType2Info	OPTIONAL
		},
		tdd								SEQUENCE {
			neighbourAndChannelIdentity		CellAndChannelIdentity					OPTIONAL
		}
	},	
	neighbourQuality					NeighbourQuality,
	sfn-SFN-ObsTimeDifference2			SFN-SFN-ObsTimeDifference2
}

Neighbour-v390ext ::=						SEQUENCE {
	modeSpecificInfo				CHOICE {
		fdd								SEQUENCE {
			frequencyInfo						FrequencyInfo
		},
		tdd								NULL
	}
}

NeighbourList ::=					SEQUENCE (SIZE (1..maxCellMeas)) OF
										Neighbour

-- The order of the cells in IE NeighbourList-v390ext shall be the
-- same as the order in IE NeighbourList
NeighbourList-v390ext ::=			SEQUENCE (SIZE (1..maxCellMeas)) OF
										Neighbour-v390ext

NeighbourQuality ::=				SEQUENCE {
	uE-Positioning-OTDOA-Quality		UE-Positioning-OTDOA-Quality
}

NewInterFreqCell ::=				SEQUENCE {
	interFreqCellID						InterFreqCellID						OPTIONAL,
	frequencyInfo						FrequencyInfo						OPTIONAL,
	cellInfo							CellInfo
}

NewInterFreqCellList ::=			SEQUENCE (SIZE (1..maxCellMeas)) OF
										NewInterFreqCell

NewInterFreqCellSI-RSCP ::=				SEQUENCE {
	interFreqCellID						InterFreqCellID						OPTIONAL,
	frequencyInfo						FrequencyInfo						OPTIONAL,
	cellInfo							CellInfoSI-RSCP
}

NewInterFreqCellSI-ECN0 ::=				SEQUENCE {
	interFreqCellID						InterFreqCellID						OPTIONAL,
	frequencyInfo						FrequencyInfo						OPTIONAL,
	cellInfo							CellInfoSI-ECN0
}

NewInterFreqCellSI-HCS-RSCP ::=				SEQUENCE {
	interFreqCellID						InterFreqCellID						OPTIONAL,
	frequencyInfo						FrequencyInfo						OPTIONAL,
	cellInfo							CellInfoSI-HCS-RSCP
}

NewInterFreqCellSI-HCS-ECN0 ::=				SEQUENCE {
	interFreqCellID						InterFreqCellID						OPTIONAL,
	frequencyInfo						FrequencyInfo						OPTIONAL,
	cellInfo							CellInfoSI-HCS-ECN0
}

NewInterFreqCellSI-List-ECN0 ::=			SEQUENCE (SIZE (1..maxCellMeas)) OF
										NewInterFreqCellSI-ECN0

NewInterFreqCellSI-List-HCS-RSCP ::=			SEQUENCE (SIZE (1..maxCellMeas)) OF
										NewInterFreqCellSI-HCS-RSCP

NewInterFreqCellSI-List-HCS-ECN0 ::=			SEQUENCE (SIZE (1..maxCellMeas)) OF
										NewInterFreqCellSI-HCS-ECN0

NewInterFreqCellSI-List-RSCP ::=		SEQUENCE (SIZE (1..maxCellMeas)) OF
										NewInterFreqCellSI-RSCP

NewInterRATCell ::=				SEQUENCE {
	interRATCellID						InterRATCellID			OPTIONAL,
	technologySpecificInfo				CHOICE {
		gsm									SEQUENCE {
			cellSelectionReselectionInfo		CellSelectReselectInfoSIB-11-12		OPTIONAL,
			interRATCellIndividualOffset		InterRATCellIndividualOffset,
			bsic								BSIC,
			frequency-band						Frequency-Band,
			bcch-ARFCN							BCCH-ARFCN,
			-- dummy is not used in this version of the specification, it should
			-- not be sent and if received it should be ignored.
			dummy								NULL				OPTIONAL
		},
		is-2000								SEQUENCE {
			is-2000SpecificMeasInfo				IS-2000SpecificMeasInfo
		},
		-- ASN.1 inconsistency: NewInterRATCellList should be optional within
		-- InterRATCellInfoList. The UE shall consider IE NewInterRATCell with
		-- technologySpecificInfo set to "absent" as valid and handle the message
		-- as if IE NewInterRATCell was absent
		absent								NULL,
		spare1								NULL
	}
}

NewInterRATCell-B ::=				SEQUENCE {
	interRATCellID						InterRATCellID				OPTIONAL,
	technologySpecificInfo				CHOICE {
		gsm									SEQUENCE {
			cellSelectionReselectionInfo		CellSelectReselectInfoSIB-11-12		OPTIONAL,
			interRATCellIndividualOffset		InterRATCellIndividualOffset,
			bsic								BSIC,
			frequency-band						Frequency-Band,
			bcch-ARFCN							BCCH-ARFCN,
			-- dummy is not used in this version of the specification, it should
			-- not be sent and if received it should be ignored.
			dummy								NULL				OPTIONAL
		},
		is-2000								SEQUENCE {
			is-2000SpecificMeasInfo				IS-2000SpecificMeasInfo
		},
		-- ASN.1 inconsistency: NewInterRATCellList-B should be optional within
		-- InterRATCellInfoList-B. UE shall consider IE NewInterRATCell-B with
		-- technologySpecificInfo set to "absent" as valid and handle the message
		-- as if IE NewInterRATCell-B was absent
		absent								NULL,
		spare1								NULL
	}
}

NewInterRATCellList ::=			SEQUENCE (SIZE (1..maxCellMeas)) OF
										NewInterRATCell

NewInterRATCellList-B ::=			SEQUENCE (SIZE (1..maxCellMeas)) OF
										NewInterRATCell-B

NewIntraFreqCell ::=				SEQUENCE {
	intraFreqCellID						IntraFreqCellID						OPTIONAL,
	cellInfo							CellInfo
}

NewIntraFreqCellList ::=			SEQUENCE (SIZE (1..maxCellMeas)) OF
										NewIntraFreqCell

NewIntraFreqCellSI-RSCP ::=				SEQUENCE {
	intraFreqCellID						IntraFreqCellID						OPTIONAL,
	cellInfo							CellInfoSI-RSCP
}

NewIntraFreqCellSI-ECN0 ::=			SEQUENCE {
	intraFreqCellID						IntraFreqCellID						OPTIONAL,
	cellInfo							CellInfoSI-ECN0
}
NewIntraFreqCellSI-HCS-RSCP ::=		SEQUENCE {
	intraFreqCellID						IntraFreqCellID						OPTIONAL,
	cellInfo							CellInfoSI-HCS-RSCP
}

NewIntraFreqCellSI-HCS-ECN0 ::=		SEQUENCE {
	intraFreqCellID						IntraFreqCellID						OPTIONAL,
	cellInfo							CellInfoSI-HCS-ECN0
}

NewIntraFreqCellSI-List-RSCP ::=		SEQUENCE (SIZE (1..maxCellMeas)) OF
											NewIntraFreqCellSI-RSCP

NewIntraFreqCellSI-List-ECN0 ::=		SEQUENCE (SIZE (1..maxCellMeas)) OF
										NewIntraFreqCellSI-ECN0

NewIntraFreqCellSI-List-HCS-RSCP ::=	SEQUENCE (SIZE (1..maxCellMeas)) OF
										NewIntraFreqCellSI-HCS-RSCP

NewIntraFreqCellSI-List-HCS-ECN0 ::=	SEQUENCE (SIZE (1..maxCellMeas)) OF
										NewIntraFreqCellSI-HCS-ECN0

NonUsedFreqParameter ::=			SEQUENCE {
	-- IE "nonUsedFreqThreshold" is not needed in case of event 2a
	-- In case of event 2a UTRAN should include value 0 within IE "nonUsedFreqThreshold"
	-- In case of event 2a, the UE shall be ignore IE "nonUsedFreqThreshold"
	-- In later versions of the message including this IE, a special version of
	-- IE "NonUsedFreqParameterList" may be defined for event 2a, namely a
	-- version not including IE "nonUsedFreqThreshold"
	nonUsedFreqThreshold				Threshold,
	nonUsedFreqW						W
}

NonUsedFreqParameterList ::=		SEQUENCE (SIZE (1..maxFreq)) OF
										NonUsedFreqParameter

ObservedTimeDifferenceToGSM ::=		INTEGER (0..4095)

OTDOA-SearchWindowSize ::=			ENUMERATED {
										c20, c40, c80, c160, c320,
										c640, c1280, moreThan1280 }

-- SPARE: Pathloss, Max = 158
-- Values above Max are spare
Pathloss ::=						INTEGER (46..173)

PenaltyTime-RSCP ::=				CHOICE {
	notUsed								NULL,
	pt10								TemporaryOffset1,
	pt20								TemporaryOffset1,
	pt30								TemporaryOffset1,
	pt40								TemporaryOffset1,
	pt50								TemporaryOffset1,
	pt60								TemporaryOffset1
}

PenaltyTime-ECN0 ::=				CHOICE {
	notUsed								NULL,
	pt10								TemporaryOffsetList,
	pt20								TemporaryOffsetList,
	pt30								TemporaryOffsetList,
	pt40								TemporaryOffsetList,
	pt50								TemporaryOffsetList,
	pt60								TemporaryOffsetList
}

PendingTimeAfterTrigger ::=			ENUMERATED {
										ptat0-25, ptat0-5, ptat1,
										ptat2, ptat4, ptat8, ptat16 }

PeriodicalOrEventTrigger ::=		ENUMERATED {
										periodical,
										eventTrigger }

PeriodicalReportingCriteria ::=		SEQUENCE {
	reportingAmount						ReportingAmount					DEFAULT ra-Infinity,
	reportingInterval					ReportingIntervalLong
}

PeriodicalWithReportingCellStatus ::= SEQUENCE {
	periodicalReportingCriteria			PeriodicalReportingCriteria,
	reportingCellStatus					ReportingCellStatus					OPTIONAL
}

PLMNIdentitiesOfNeighbourCells ::=	SEQUENCE {
		plmnsOfIntraFreqCellsList		PLMNsOfIntraFreqCellsList			OPTIONAL,
		plmnsOfInterFreqCellsList		PLMNsOfInterFreqCellsList			OPTIONAL,
		plmnsOfInterRATCellsList		PLMNsOfInterRATCellsList			OPTIONAL
}

PLMNsOfInterFreqCellsList ::=			SEQUENCE (SIZE (1..maxCellMeas)) OF
											SEQUENCE {
	plmn-Identity								PLMN-Identity				OPTIONAL
}

PLMNsOfIntraFreqCellsList ::=			SEQUENCE (SIZE (1..maxCellMeas)) OF
											SEQUENCE {
	plmn-Identity								PLMN-Identity				OPTIONAL
}

PLMNsOfInterRATCellsList ::=			SEQUENCE (SIZE (1..maxCellMeas)) OF
											SEQUENCE {
	plmn-Identity								PLMN-Identity				OPTIONAL
}

PositionEstimate ::=				CHOICE {
	ellipsoidPoint						EllipsoidPoint,
	ellipsoidPointUncertCircle			EllipsoidPointUncertCircle,
	ellipsoidPointUncertEllipse			EllipsoidPointUncertEllipse,
	ellipsoidPointAltitude				EllipsoidPointAltitude,
	ellipsoidPointAltitudeEllipse		EllipsoidPointAltitudeEllipsoide
}

PositioningMethod ::=				ENUMERATED {
										otdoa,
										gps,
										otdoaOrGPS, cellID }

-- Actual value PRC = IE value * 0.32
PRC ::=								INTEGER (-2047..2047)

-- SPARE: PrimaryCCPCH-RSCP, Max = 91
-- Values above Max are spare
PrimaryCCPCH-RSCP ::=				INTEGER (0..127)

Q-HCS ::=							INTEGER (0..99)

Q-OffsetS-N ::=						INTEGER (-50..50)

Q-QualMin ::=						INTEGER (-24..0)

-- Actual value Q-RxlevMin = (IE value * 2) + 1
Q-RxlevMin ::=						INTEGER (-58..-13)

QualityEventResults ::=				SEQUENCE (SIZE (1..maxTrCH)) OF
										TransportChannelIdentity

QualityMeasuredResults ::=			SEQUENCE {
	blerMeasurementResultsList			BLER-MeasurementResultsList			OPTIONAL,
	modeSpecificInfo					CHOICE {
		fdd									NULL,
		tdd									SEQUENCE {
			sir-MeasurementResults				SIR-MeasurementList			OPTIONAL
		}
	}
}

QualityMeasurement ::=				SEQUENCE {
	qualityReportingQuantity			QualityReportingQuantity			OPTIONAL,
	reportCriteria						QualityReportCriteria
}

QualityReportCriteria ::=			CHOICE {
	qualityReportingCriteria			QualityReportingCriteria,
	periodicalReportingCriteria			PeriodicalReportingCriteria,
	noReporting							NULL
}

QualityReportingCriteria ::=		SEQUENCE (SIZE (1..maxTrCH)) OF
										QualityReportingCriteriaSingle

QualityReportingCriteriaSingle ::=	SEQUENCE {
	transportChannelIdentity			TransportChannelIdentity,
	totalCRC							INTEGER (1..512),
	badCRC								INTEGER (1..512),
	pendingAfterTrigger					INTEGER (1..512)
}

QualityReportingQuantity ::=		SEQUENCE {
	dl-TransChBLER						BOOLEAN,
	bler-dl-TransChIdList				BLER-TransChIdList					OPTIONAL,
	modeSpecificInfo					CHOICE {
		fdd									NULL,
		tdd									SEQUENCE {
			sir-TFCS-List						SIR-TFCS-List				OPTIONAL
		}
	}
}

RAT-Type ::=						ENUMERATED {
										gsm, is2000 }

ReferenceCellPosition ::=			CHOICE {
	ellipsoidPoint						EllipsoidPoint,
	ellipsoidPointWithAltitude			EllipsoidPointAltitude
}


-- ReferenceLocation, as defined in 23.032
ReferenceLocation ::=			SEQUENCE {
	ellipsoidPointAltitudeEllipsoide		EllipsoidPointAltitudeEllipsoide
}

ReferenceTimeDifferenceToCell ::=	CHOICE {
	-- Actual value accuracy40 = IE value * 40
	accuracy40							INTEGER (0..960),
	-- Actual value accuracy256 = IE value * 256
	accuracy256							INTEGER (0..150),
	-- Actual value accuracy2560 = IE value * 2560
	accuracy2560						INTEGER (0..15)
}

RemovedInterFreqCellList ::=		CHOICE {
	removeAllInterFreqCells				NULL,
	removeSomeInterFreqCells			SEQUENCE (SIZE (1..maxCellMeas)) OF
											InterFreqCellID,
	removeNoInterFreqCells				NULL
}

RemovedInterRATCellList ::=		CHOICE {
	removeAllInterRATCells			NULL,
	removeSomeInterRATCells			SEQUENCE (SIZE (1..maxCellMeas)) OF
											InterRATCellID,
	removeNoInterRATCells			NULL
}

RemovedIntraFreqCellList ::=		CHOICE {
	removeAllIntraFreqCells				NULL,
	removeSomeIntraFreqCells			SEQUENCE (SIZE (1..maxCellMeas)) OF
											IntraFreqCellID,
	removeNoIntraFreqCells				NULL
}

ReplacementActivationThreshold ::=	ENUMERATED {
										notApplicable, t1, t2,
										t3, t4, t5, t6, t7 }

ReportDeactivationThreshold ::=		ENUMERATED {
										notApplicable, t1, t2,
										t3, t4, t5, t6, t7 }

ReportingAmount ::=					ENUMERATED {
										ra1, ra2, ra4, ra8, ra16, ra32,
										ra64, ra-Infinity }

ReportingCellStatus ::=				CHOICE{
	withinActiveSet						MaxNumberOfReportingCellsType1,
	withinMonitoredSetUsedFreq			MaxNumberOfReportingCellsType1,
	withinActiveAndOrMonitoredUsedFreq	MaxNumberOfReportingCellsType1,
	withinDetectedSetUsedFreq			MaxNumberOfReportingCellsType1,
	withinMonitoredAndOrDetectedUsedFreq
										MaxNumberOfReportingCellsType1,
	allActiveplusMonitoredSet			MaxNumberOfReportingCellsType3,
	allActivePlusDetectedSet			MaxNumberOfReportingCellsType3,
	allActivePlusMonitoredAndOrDetectedSet
										MaxNumberOfReportingCellsType3,
	withinVirtualActSet				MaxNumberOfReportingCellsType1,
	withinMonitoredSetNonUsedFreq		MaxNumberOfReportingCellsType1,
	withinMonitoredAndOrVirtualActiveSetNonUsedFreq
										MaxNumberOfReportingCellsType1,
	allVirtualActSetplusMonitoredSetNonUsedFreq	
										MaxNumberOfReportingCellsType3,
	withinActSetOrVirtualActSet-InterRATcells
										MaxNumberOfReportingCellsType2,
	withinActSetAndOrMonitoredUsedFreqOrVirtualActSetAndOrMonitoredNonUsedFreq	
										MaxNumberOfReportingCellsType2
}

ReportingCellStatusOpt ::=			SEQUENCE {
	reportingCellStatus					ReportingCellStatus					OPTIONAL
}


ReportingInfoForCellDCH ::=			SEQUENCE {
	intraFreqReportingQuantity			IntraFreqReportingQuantity,
	measurementReportingMode			MeasurementReportingMode,
	reportCriteria						CellDCH-ReportCriteria
}

ReportingInterval ::=				ENUMERATED {
										noPeriodicalreporting, ri0-25,
										ri0-5, ri1, ri2, ri4, ri8, ri16 }

ReportingIntervalLong ::=			ENUMERATED {
										ril0, ril0-25, ril0-5, ril1,
										ril2, ril3, ril4, ril6, ril8,
										ril12, ril16, ril20, ril24,
										ril28, ril32, ril64 }
									-- When the value "ril0" is used, the UE behaviour is not
									-- defined.

-- Actual value ReportingRange = IE value * 0.5
ReportingRange ::=					INTEGER (0..29)

RL-AdditionInfoList ::=				SEQUENCE (SIZE (1..maxRL)) OF
										PrimaryCPICH-Info

RL-InformationLists ::=				SEQUENCE {
	rl-AdditionInfoList					RL-AdditionInfoList					OPTIONAL,
	rl-RemovalInformationList			RL-RemovalInformationList			OPTIONAL
}

RLC-BuffersPayload ::=				ENUMERATED {
										pl0, pl4, pl8, pl16, pl32,
										pl64, pl128, pl256, pl512, pl1024,
										pl2k, pl4k, pl8k, pl16k, pl32k,
										pl64k, pl128k, pl256k, pl512k, pl1024k,
										spare12, spare11, spare10, spare9, spare8,
										spare7, spare6, spare5, spare4, spare3,
										spare2, spare1 }

-- Actual value RRC = IE value * 0.032
RRC ::=								INTEGER (-127..127)

SatData ::=							SEQUENCE{
	satID								SatID,
	iode								IODE
}

SatDataList ::=						SEQUENCE (SIZE (0..maxSat)) OF
										SatData

SatelliteStatus ::=					ENUMERATED {
										ns-NN-U,
										es-SN,
										es-NN-U,
										rev2,
										rev }

SatID ::=							INTEGER (0..63)

SFN-SFN-Drift ::=					ENUMERATED {
									sfnsfndrift0, sfnsfndrift1, sfnsfndrift2, sfnsfndrift3,
									sfnsfndrift4, sfnsfndrift5, sfnsfndrift8, sfnsfndrift10,
									sfnsfndrift15, sfnsfndrift25, sfnsfndrift35, sfnsfndrift50,
									sfnsfndrift65, sfnsfndrift80, sfnsfndrift100, sfnsfndrift-1,
									sfnsfndrift-2, sfnsfndrift-3, sfnsfndrift-4, sfnsfndrift-5,
									sfnsfndrift-8, sfnsfndrift-10, sfnsfndrift-15, sfnsfndrift-25,
									sfnsfndrift-35, sfnsfndrift-50, sfnsfndrift-65, sfnsfndrift-80,
									sfnsfndrift-100}

SFN-SFN-ObsTimeDifference ::=		CHOICE {
	type1								SFN-SFN-ObsTimeDifference1,
	type2								SFN-SFN-ObsTimeDifference2
}

-- SPARE: SFN-SFN-ObsTimeDifference1, Max = 9830399
-- Values above Max are spare
SFN-SFN-ObsTimeDifference1 ::=		INTEGER (0..16777215)

-- SPARE: SFN-SFN-ObsTimeDifference2, Max = 40961
-- Values above Max are spare
SFN-SFN-ObsTimeDifference2 ::=		INTEGER (0..65535)

SFN-SFN-OTD-Type ::=				ENUMERATED {
										noReport,
										type1,
										type2 }

SFN-Offset-Validity	::=				ENUMERATED { false }

SFN-SFN-RelTimeDifference1 ::=		SEQUENCE {
	sfn-Offset							INTEGER (0 .. 4095),
	sfn-sfn-Reltimedifference			INTEGER (0.. 38399)
}

SFN-TOW-Uncertainty	::=				ENUMERATED {
										lessThan10,
										moreThan10 }

SIR ::=								INTEGER (0..63)


SIR-MeasurementList ::=				SEQUENCE (SIZE (1..maxCCTrCH)) OF
										SIR-MeasurementResults


SIR-MeasurementResults ::=			SEQUENCE {
	tfcs-ID								TFCS-IdentityPlain,
	sir-TimeslotList					SIR-TimeslotList
}

SIR-TFCS ::=						TFCS-IdentityPlain


SIR-TFCS-List ::=					SEQUENCE (SIZE (1..maxCCTrCH)) OF
										SIR-TFCS

SIR-TimeslotList ::=				SEQUENCE (SIZE (1..maxTS)) OF
										SIR

-- SubFrame1Reserved, reserved bits in subframe 1 of the GPS navigation message
SubFrame1Reserved ::=				SEQUENCE {
	reserved1							BIT STRING (SIZE (23)),
	reserved2							BIT STRING (SIZE (24)),
	reserved3							BIT STRING (SIZE (24)),
	reserved4							BIT STRING (SIZE (16))
}

T-CRMax ::=							CHOICE {
	notUsed								NULL,
	t30									N-CR-T-CRMaxHyst,
	t60									N-CR-T-CRMaxHyst,
	t120								N-CR-T-CRMaxHyst,
	t180								N-CR-T-CRMaxHyst,
	t240								N-CR-T-CRMaxHyst
}

T-CRMaxHyst ::=						ENUMERATED {
										notUsed, t10, t20, t30,
										t40, t50, t60, t70 }

TemporaryOffset1 ::=				ENUMERATED {
										to3, to6, to9, to12, to15,
										to18, to21, infinite }

TemporaryOffset2 ::=				ENUMERATED {
										to2, to3, to4, to6, to8,
										to10, to12, infinite }

TemporaryOffsetList ::=				SEQUENCE	{
		temporaryOffset1				TemporaryOffset1,
		temporaryOffset2				TemporaryOffset2
}

Threshold ::=						INTEGER (-115..0)

ThresholdPositionChange ::=			ENUMERATED {
										pc10, pc20, pc30, pc40, pc50,
										pc100, pc200, pc300, pc500,
										pc1000, pc2000, pc5000, pc10000,
										pc20000, pc50000, pc100000 }

ThresholdSFN-GPS-TOW ::=			ENUMERATED {
										ms1, ms2, ms3, ms5, ms10,
										ms20, ms50, ms100 }

ThresholdSFN-SFN-Change ::=			ENUMERATED {
										c0-25, c0-5, c1, c2, c3, c4, c5,
										c10, c20, c50, c100, c200, c500,
										c1000, c2000, c5000 }

ThresholdUsedFrequency ::=			INTEGER (-115..165)

-- Actual value TimeInterval = IE value * 20.
TimeInterval ::=					INTEGER (1..13)

TimeslotInfo ::=					SEQUENCE {
	timeslotNumber						TimeslotNumber,
	burstType							BurstType
}

TimeslotInfoList ::=				SEQUENCE (SIZE (1..maxTS)) OF
										TimeslotInfo

-- SPARE: TimeslotISCP, Max = 91
-- Values above Max are spare
TimeslotISCP ::=					INTEGER (0..127)

TimeslotISCP-List ::=				SEQUENCE (SIZE (1..maxTS)) OF
										TimeslotISCP

TimeslotListWithISCP ::=			SEQUENCE (SIZE (1..maxTS)) OF
										TimeslotWithISCP

TimeslotWithISCP ::=				SEQUENCE {
	timeslot							TimeslotNumber,
	timeslotISCP						TimeslotISCP
}

TimeToTrigger ::=					ENUMERATED {
										ttt0, ttt10, ttt20, ttt40, ttt60,
										ttt80, ttt100, ttt120, ttt160,
										ttt200, ttt240, tt320, ttt640,
										ttt1280, ttt2560, ttt5000 }

TrafficVolumeEventParam ::=			SEQUENCE {
	eventID								TrafficVolumeEventType,
	reportingThreshold					TrafficVolumeThreshold,
	timeToTrigger						TimeToTrigger						OPTIONAL,
	pendingTimeAfterTrigger				PendingTimeAfterTrigger				OPTIONAL,
	tx-InterruptionAfterTrigger			TX-InterruptionAfterTrigger			OPTIONAL
}

TrafficVolumeEventResults ::=		SEQUENCE {
	ul-transportChannelCausingEvent		UL-TrCH-Identity,
	trafficVolumeEventIdentity			TrafficVolumeEventType
}

TrafficVolumeEventType ::=			ENUMERATED {
										e4a,
										e4b }

TrafficVolumeMeasQuantity ::=		CHOICE {
	rlc-BufferPayload					NULL,
	averageRLC-BufferPayload			TimeInterval,
	varianceOfRLC-BufferPayload			TimeInterval
}

TrafficVolumeMeasSysInfo ::=		SEQUENCE {
	trafficVolumeMeasurementID			MeasurementIdentity			DEFAULT 4,
	trafficVolumeMeasurementObjectList	TrafficVolumeMeasurementObjectList	OPTIONAL,
	trafficVolumeMeasQuantity			TrafficVolumeMeasQuantity			OPTIONAL,
	trafficVolumeReportingQuantity		TrafficVolumeReportingQuantity		OPTIONAL,
	-- dummy is not used in this version of specification, it should
	-- not be sent and if received it should be ignored.
	dummy								TrafficVolumeReportingCriteria		OPTIONAL,
	measurementValidity					MeasurementValidity					OPTIONAL,
	measurementReportingMode			MeasurementReportingMode,
	reportCriteriaSysInf				TrafficVolumeReportCriteriaSysInfo

}

TrafficVolumeMeasuredResults ::=	SEQUENCE {
	rb-Identity							RB-Identity,
	rlc-BuffersPayload					RLC-BuffersPayload					OPTIONAL,
	averageRLC-BufferPayload			AverageRLC-BufferPayload			OPTIONAL,
	varianceOfRLC-BufferPayload			VarianceOfRLC-BufferPayload			OPTIONAL
}

TrafficVolumeMeasuredResultsList ::= SEQUENCE (SIZE (1..maxRB)) OF
										TrafficVolumeMeasuredResults

TrafficVolumeMeasurement ::=		SEQUENCE {
	trafficVolumeMeasurementObjectList	TrafficVolumeMeasurementObjectList	OPTIONAL,
	trafficVolumeMeasQuantity			TrafficVolumeMeasQuantity			OPTIONAL,
	trafficVolumeReportingQuantity		TrafficVolumeReportingQuantity		OPTIONAL,
	measurementValidity					MeasurementValidity					OPTIONAL,
	reportCriteria						TrafficVolumeReportCriteria
}

TrafficVolumeMeasurementObjectList ::= SEQUENCE (SIZE (1..maxTrCH)) OF
											UL-TrCH-Identity

TrafficVolumeReportCriteria ::=		CHOICE {
	trafficVolumeReportingCriteria		TrafficVolumeReportingCriteria,
	periodicalReportingCriteria			PeriodicalReportingCriteria,
	noReporting							NULL
}

TrafficVolumeReportCriteriaSysInfo ::=	CHOICE {
	trafficVolumeReportingCriteria		TrafficVolumeReportingCriteria,
	periodicalReportingCriteria			PeriodicalReportingCriteria
}

TrafficVolumeReportingCriteria ::= SEQUENCE {
	-- NOTE: transChCriteriaList should be mandatory in later versions of this message
	transChCriteriaList					TransChCriteriaList					OPTIONAL
}

TrafficVolumeReportingQuantity ::= SEQUENCE {
	rlc-RB-BufferPayload				BOOLEAN,
	rlc-RB-BufferPayloadAverage			BOOLEAN,
	rlc-RB-BufferPayloadVariance		BOOLEAN
}

TrafficVolumeThreshold ::=			ENUMERATED {
										th8, th16, th32, th64, th128,
										th256, th512, th1024, th2k, th3k,
										th4k, th6k, th8k, th12k, th16k,
										th24k, th32k, th48k, th64k, th96k,
										th128k, th192k, th256k, th384k,
										th512k, th768k }

TransChCriteria ::=					SEQUENCE {
	ul-transportChannelID				UL-TrCH-Identity					OPTIONAL,
	eventSpecificParameters				SEQUENCE (SIZE (1..maxMeasParEvent)) OF
											TrafficVolumeEventParam			OPTIONAL
}

TransChCriteriaList ::=			SEQUENCE (SIZE (1..maxTrCH)) OF
										TransChCriteria

TransferMode ::=					ENUMERATED {
										acknowledgedModeRLC,
										unacknowledgedModeRLC }

TransmittedPowerThreshold ::=		INTEGER (-50..33)

TriggeringCondition1 ::=			ENUMERATED {
										activeSetCellsOnly,
										monitoredSetCellsOnly,
										activeSetAndMonitoredSetCells }

TriggeringCondition2 ::=			ENUMERATED {
										activeSetCellsOnly,
										monitoredSetCellsOnly,
										activeSetAndMonitoredSetCells,
										detectedSetCellsOnly,
										detectedSetAndMonitoredSetCells }

TX-InterruptionAfterTrigger ::=		ENUMERATED {
										txiat0-25, txiat0-5, txiat1,
										txiat2, txiat4, txiat8, txiat16 }

UDRE ::=							ENUMERATED {
										lessThan1,
										between1-and-4,
										between4-and-8,
										over8 }

UE-6AB-Event ::=					SEQUENCE {
	timeToTrigger						TimeToTrigger,
	transmittedPowerThreshold			TransmittedPowerThreshold
}

UE-6FG-Event ::=					SEQUENCE {
	timeToTrigger						TimeToTrigger,
	ue-RX-TX-TimeDifferenceThreshold	UE-RX-TX-TimeDifferenceThreshold
}

UE-AutonomousUpdateMode ::=			CHOICE {
	on									NULL,
	onWithNoReporting					NULL,
	off								RL-InformationLists
}

UE-InternalEventParam ::=			CHOICE {
	event6a								UE-6AB-Event,
	event6b								UE-6AB-Event,
	event6c								TimeToTrigger,
	event6d								TimeToTrigger,
	event6e								TimeToTrigger,
	event6f								UE-6FG-Event,
	event6g								UE-6FG-Event
}

UE-InternalEventParamList ::=		SEQUENCE (SIZE (1..maxMeasEvent)) OF
										UE-InternalEventParam

UE-InternalEventResults ::=			CHOICE {
	event6a								NULL,
	event6b								NULL,
	event6c								NULL,
	event6d								NULL,
	event6e								NULL,
	event6f								PrimaryCPICH-Info,
	event6g								PrimaryCPICH-Info,
	spare								NULL
}

UE-InternalMeasQuantity ::=			SEQUENCE {
	measurementQuantity					UE-MeasurementQuantity,
	filterCoefficient					FilterCoefficient					DEFAULT fc0
}

UE-InternalMeasuredResults ::=		SEQUENCE {
	modeSpecificInfo					CHOICE {
		fdd									SEQUENCE {
			ue-TransmittedPowerFDD				UE-TransmittedPower			OPTIONAL,
			ue-RX-TX-ReportEntryList			UE-RX-TX-ReportEntryList	OPTIONAL
		},
		tdd									SEQUENCE {
			ue-TransmittedPowerTDD-List			UE-TransmittedPowerTDD-List	OPTIONAL,
			appliedTA							UL-TimingAdvance			OPTIONAL
		}
	}
}

UE-InternalMeasurement ::=			SEQUENCE {
	ue-InternalMeasQuantity				UE-InternalMeasQuantity				OPTIONAL,
	ue-InternalReportingQuantity		UE-InternalReportingQuantity		OPTIONAL,
	reportCriteria						UE-InternalReportCriteria
}

UE-InternalMeasurementSysInfo ::=	SEQUENCE {
	ue-InternalMeasurementID			MeasurementIdentity			DEFAULT 5,
	ue-InternalMeasQuantity				UE-InternalMeasQuantity
}

UE-InternalReportCriteria ::=		CHOICE {
	ue-InternalReportingCriteria		UE-InternalReportingCriteria,
	periodicalReportingCriteria			PeriodicalReportingCriteria,
	noReporting							NULL
}

UE-InternalReportingCriteria ::=	SEQUENCE {
	ue-InternalEventParamList			UE-InternalEventParamList			OPTIONAL
}

UE-InternalReportingQuantity ::=	SEQUENCE {
	ue-TransmittedPower					BOOLEAN,
	modeSpecificInfo					CHOICE {
		fdd									SEQUENCE {
			ue-RX-TX-TimeDifference				BOOLEAN
		},
		tdd									SEQUENCE {
			appliedTA							BOOLEAN
		}
	}
}

-- TABULAR: UE-MeasurementQuantity, for TDD only the values
-- ue-TransmittedPower and utra-Carrier-RSSI are used.
UE-MeasurementQuantity ::=			ENUMERATED {
										ue-TransmittedPower,
										utra-Carrier-RSSI,
										ue-RX-TX-TimeDifference }

UE-RX-TX-ReportEntry ::=			SEQUENCE {
	primaryCPICH-Info					PrimaryCPICH-Info,
	ue-RX-TX-TimeDifferenceType1		UE-RX-TX-TimeDifferenceType1
}

UE-RX-TX-ReportEntryList ::=		SEQUENCE (SIZE (1..maxRL)) OF
										UE-RX-TX-ReportEntry

-- SPARE: UE-RX-TX-TimeDifferenceType1, Max = 1280
-- Values above Max are spare
UE-RX-TX-TimeDifferenceType1 ::=			INTEGER (768..1791)

-- Actual value UE-RX-TX-TimeDifferenceType2 = IE value * 0.0625 + 768
UE-RX-TX-TimeDifferenceType2 ::=	INTEGER (0..8191)

UE-RX-TX-TimeDifferenceType2Info ::=	SEQUENCE {
	ue-RX-TX-TimeDifferenceType2			UE-RX-TX-TimeDifferenceType2,
	neighbourQuality						NeighbourQuality
}

UE-RX-TX-TimeDifferenceThreshold ::= INTEGER (768..1280)

UE-TransmittedPower ::=				INTEGER (0..104)

UE-TransmittedPowerTDD-List ::=		SEQUENCE (SIZE (1..maxTS)) OF
										UE-TransmittedPower

UL-TrCH-Identity ::=					CHOICE{
	dch									TransportChannelIdentity,
	-- Default transport channel in the UL is either RACH or CPCH, but not both.
	rachorcpch							NULL,
	usch								TransportChannelIdentity
}

UE-Positioning-Accuracy ::=					BIT STRING (SIZE (7))


UE-Positioning-CipherParameters ::=			SEQUENCE {
	cipheringKeyFlag					BIT STRING (SIZE (1)),
	cipheringSerialNumber				INTEGER (0..65535)
}

UE-Positioning-Error ::=						SEQUENCE {
	errorReason							UE-Positioning-ErrorCause,
	ue-positioning-GPS-additionalAssistanceDataRequest			UE-Positioning-GPS-AdditionalAssistanceDataRequest	OPTIONAL
}

UE-Positioning-ErrorCause ::=					ENUMERATED {
										notEnoughOTDOA-Cells,
										notEnoughGPS-Satellites,
										assistanceDataMissing,
										notAccomplishedGPS-TimingOfCellFrames,
										undefinedError,
										requestDeniedByUser,
										notProcessedAndTimeout,
										referenceCellNotServingCell }

UE-Positioning-EventParam ::=					SEQUENCE {
	reportingAmount						ReportingAmount,
	reportFirstFix						BOOLEAN,
	measurementInterval					UE-Positioning-MeasurementInterval,
	eventSpecificInfo					UE-Positioning-EventSpecificInfo
}

UE-Positioning-EventParamList ::=				SEQUENCE (SIZE (1..maxMeasEvent)) OF
										UE-Positioning-EventParam

UE-Positioning-EventSpecificInfo ::=			CHOICE {
	e7a									ThresholdPositionChange,
	e7b									ThresholdSFN-SFN-Change,
	e7c									ThresholdSFN-GPS-TOW
}

UE-Positioning-GPS-AcquisitionAssistance ::=	SEQUENCE {
	gps-ReferenceTime				INTEGER (0..604799999),
	utran-GPSReferenceTime				UTRAN-GPSReferenceTime			OPTIONAL,
	satelliteInformationList			AcquisitionSatInfoList
}

UE-Positioning-GPS-AdditionalAssistanceDataRequest ::=		SEQUENCE {
	almanacRequest						BOOLEAN,
	utcModelRequest						BOOLEAN,
	ionosphericModelRequest				BOOLEAN,
	navigationModelRequest				BOOLEAN,
	dgpsCorrectionsRequest				BOOLEAN,
	referenceLocationRequest			BOOLEAN,
	referenceTimeRequest				BOOLEAN,
	aquisitionAssistanceRequest			BOOLEAN,
	realTimeIntegrityRequest			BOOLEAN,
	navModelAddDataRequest				UE-Positioning-GPS-NavModelAddDataReq		OPTIONAL
}

UE-Positioning-GPS-Almanac ::=					SEQUENCE {
	wn-a								BIT STRING (SIZE (8)),
	almanacSatInfoList					AlmanacSatInfoList,
	sv-GlobalHealth						BIT STRING (SIZE (364))				OPTIONAL
}

UE-Positioning-GPS-AssistanceData ::=			SEQUENCE {
	ue-positioning-GPS-ReferenceTime				UE-Positioning-GPS-ReferenceTime				OPTIONAL,
	ue-positioning-GPS-ReferenceLocation			ReferenceLocation				OPTIONAL,
	ue-positioning-GPS-DGPS-Corrections				UE-Positioning-GPS-DGPS-Corrections				OPTIONAL,
	ue-positioning-GPS-NavigationModel				UE-Positioning-GPS-NavigationModel				OPTIONAL,
	ue-positioning-GPS-IonosphericModel				UE-Positioning-GPS-IonosphericModel				OPTIONAL,
	ue-positioning-GPS-UTC-Model					UE-Positioning-GPS-UTC-Model					OPTIONAL,
	ue-positioning-GPS-Almanac						UE-Positioning-GPS-Almanac						OPTIONAL,
	ue-positioning-GPS-AcquisitionAssistance		UE-Positioning-GPS-AcquisitionAssistance		OPTIONAL,
	ue-positioning-GPS-Real-timeIntegrity			BadSatList							OPTIONAL,
	-- dummy is not used in this version of the specification, it should
	-- not be sent and if received it should be ignored.
	dummy			UE-Positioning-GPS-ReferenceCellInfo		OPTIONAL
}

UE-Positioning-GPS-DGPS-Corrections ::=		SEQUENCE {
	gps-TOW								INTEGER (0..604799),
	statusHealth						DiffCorrectionStatus,
	dgps-CorrectionSatInfoList			DGPS-CorrectionSatInfoList
}

UE-Positioning-GPS-IonosphericModel ::=		SEQUENCE {
	alfa0								BIT STRING (SIZE (8)),
	alfa1								BIT STRING (SIZE (8)),
	alfa2								BIT STRING (SIZE (8)),
	alfa3								BIT STRING (SIZE (8)),
	beta0								BIT STRING (SIZE (8)),
	beta1								BIT STRING (SIZE (8)),
	beta2								BIT STRING (SIZE (8)),
	beta3								BIT STRING (SIZE (8))
}

UE-Positioning-GPS-MeasurementResults ::=				SEQUENCE {
	referenceTime						CHOICE {
		utran-GPSReferenceTimeResult		UTRAN-GPSReferenceTimeResult,
		gps-ReferenceTimeOnly				INTEGER (0..604799999)
	},
	gps-MeasurementParamList			GPS-MeasurementParamList
}

UE-Positioning-GPS-NavigationModel ::=			SEQUENCE {
	navigationModelSatInfoList			NavigationModelSatInfoList
}

UE-Positioning-GPS-NavModelAddDataReq ::=		SEQUENCE {
	gps-Week							INTEGER (0..1023),
	-- SPARE: gps-Toe, Max = 167
	-- Values above Max are spare
	gps-Toe								INTEGER (0..255),
	-- SPARE: tToeLimit, Max = 10
	-- Values above Max are spare
	tToeLimit							INTEGER (0..15),
	satDataList							SatDataList
}

UE-Positioning-GPS-ReferenceCellInfo ::=		SEQUENCE{
	modeSpecificInfo				CHOICE {
		fdd								SEQUENCE {
			referenceIdentity				PrimaryCPICH-Info
		},
		tdd								SEQUENCE {
			referenceIdentity				CellParametersID
		}
	}
}

UE-Positioning-GPS-ReferenceTime ::=			SEQUENCE {
	gps-Week							INTEGER (0..1023),
	gps-tow-1msec						GPS-TOW-1msec,
	utran-GPSReferenceTime				UTRAN-GPSReferenceTime				OPTIONAL,
	sfn-tow-Uncertainty					SFN-TOW-Uncertainty					OPTIONAL,
	utran-GPS-DriftRate					UTRAN-GPS-DriftRate					OPTIONAL,
	gps-TOW-AssistList					GPS-TOW-AssistList					OPTIONAL
}

UE-Positioning-GPS-UTC-Model ::=				SEQUENCE {
	a1									BIT STRING (SIZE (24)),
	a0									BIT STRING (SIZE (32)),
	t-ot								BIT STRING (SIZE (8)),
	wn-t								BIT STRING (SIZE (8)),
	delta-t-LS							BIT STRING (SIZE (8)),
	wn-lsf								BIT STRING (SIZE (8)),
	dn									BIT STRING (SIZE (8)),
	delta-t-LSF							BIT STRING (SIZE (8))
}

UE-Positioning-IPDL-Parameters ::=				SEQUENCE {
	ip-Spacing							IP-Spacing,
	ip-Length							IP-Length,
	ip-Offset							INTEGER (0..9),
	seed								INTEGER (0..63),
	burstModeParameters					BurstModeParameters		OPTIONAL
}

UE-Positioning-MeasuredResults ::=				SEQUENCE {
	ue-positioning-OTDOA-Measurement				UE-Positioning-OTDOA-Measurement				OPTIONAL,
	ue-positioning-PositionEstimateInfo				UE-Positioning-PositionEstimateInfo						OPTIONAL,
	ue-positioning-GPS-Measurement					UE-Positioning-GPS-MeasurementResults			OPTIONAL,
	ue-positioning-Error							UE-Positioning-Error							OPTIONAL
}

UE-Positioning-MeasuredResults-v390ext ::=		SEQUENCE {
	ue-Positioning-OTDOA-Measurement-v390ext		UE-Positioning-OTDOA-Measurement-v390ext
}

UE-Positioning-Measurement ::=					SEQUENCE {
	ue-positioning-ReportingQuantity				UE-Positioning-ReportingQuantity,
	reportCriteria						UE-Positioning-ReportCriteria,
	ue-positioning-OTDOA-AssistanceData			UE-Positioning-OTDOA-AssistanceData			OPTIONAL,
	ue-positioning-GPS-AssistanceData				UE-Positioning-GPS-AssistanceData				OPTIONAL
}

UE-Positioning-Measurement-v390ext ::=			SEQUENCE {
	ue-positioning-ReportingQuantity-v390ext		UE-Positioning-ReportingQuantity-v390ext			OPTIONAL,
	measurementValidity					MeasurementValidity					OPTIONAL,
	ue-positioning-OTDOA-AssistanceData-UEB			UE-Positioning-OTDOA-AssistanceData-UEB		
	OPTIONAL
}

UE-Positioning-MeasurementEventResults ::=		CHOICE {
	event7a								UE-Positioning-PositionEstimateInfo,
	event7b								UE-Positioning-OTDOA-Measurement,
	event7c								UE-Positioning-GPS-MeasurementResults,
	spare								NULL	
}

UE-Positioning-MeasurementInterval ::=			ENUMERATED {
										e5, e15, e60, e300,
										e900, e1800, e3600, e7200 }

UE-Positioning-MethodType ::=					ENUMERATED {
										ue-Assisted,
										ue-Based,
										ue-BasedPreferred,
										ue-AssistedPreferred }

UE-Positioning-OTDOA-AssistanceData ::=		SEQUENCE {
	ue-positioning-OTDOA-ReferenceCellInfo			UE-Positioning-OTDOA-ReferenceCellInfo				OPTIONAL,
	ue-positioning-OTDOA-NeighbourCellList				UE-Positioning-OTDOA-NeighbourCellList				OPTIONAL
}

UE-Positioning-OTDOA-AssistanceData-UEB ::=		SEQUENCE {
	ue-positioning-OTDOA-ReferenceCellInfo-UEB			UE-Positioning-OTDOA-ReferenceCellInfo-UEB				OPTIONAL,
	ue-positioning-OTDOA-NeighbourCellList-UEB			UE-Positioning-OTDOA-NeighbourCellList-UEB				OPTIONAL
}

UE-Positioning-OTDOA-Measurement ::=			SEQUENCE {
	sfn									INTEGER (0..4095),
	modeSpecificInfo				CHOICE {
		fdd								SEQUENCE {
			referenceCellIDentity				PrimaryCPICH-Info,
			ue-RX-TX-TimeDifferenceType2Info	UE-RX-TX-TimeDifferenceType2Info
		},
		tdd								SEQUENCE {
			referenceCellIdentity			CellParametersID
		}	},
	neighbourList						NeighbourList						OPTIONAL
}

UE-Positioning-OTDOA-Measurement-v390ext ::=			SEQUENCE {
	neighbourList-v390ext				NeighbourList-v390ext
}

UE-Positioning-OTDOA-NeighbourCellInfo  ::= SEQUENCE {
	modeSpecificInfo	CHOICE	{
		fdd								SEQUENCE {
			primaryCPICH-Info					PrimaryCPICH-Info
		},
		tdd								SEQUENCE{
			cellAndChannelIdentity				CellAndChannelIdentity
		}
	},
	frequencyInfo						FrequencyInfo						OPTIONAL,
	ue-positioning-IPDL-Paremeters					UE-Positioning-IPDL-Parameters					OPTIONAL,
	sfn-SFN-RelTimeDifference			SFN-SFN-RelTimeDifference1,
	sfn-SFN-Drift						SFN-SFN-Drift		OPTIONAL,
	searchWindowSize					OTDOA-SearchWindowSize,
	positioningMode	CHOICE{
		ueBased									SEQUENCE {},
		ueAssisted								SEQUENCE {}
	}
}

UE-Positioning-OTDOA-NeighbourCellInfo-UEB  ::= SEQUENCE {
	modeSpecificInfo	CHOICE	{
		fdd								SEQUENCE {
			primaryCPICH-Info					PrimaryCPICH-Info
		},
		tdd								SEQUENCE{
			cellAndChannelIdentity				CellAndChannelIdentity
		}
	},
	frequencyInfo						FrequencyInfo						OPTIONAL,
	ue-positioning-IPDL-Paremeters		UE-Positioning-IPDL-Parameters		OPTIONAL,
	sfn-SFN-RelTimeDifference			SFN-SFN-RelTimeDifference1,
	sfn-SFN-Drift						SFN-SFN-Drift						OPTIONAL,
	searchWindowSize					OTDOA-SearchWindowSize,
	relativeNorth						INTEGER (-20000..20000)				OPTIONAL,
	relativeEast						INTEGER (-20000..20000)				OPTIONAL,
	relativeAltitude					INTEGER (-4000..4000)				OPTIONAL,
	fineSFN-SFN							FineSFN-SFN,
	-- Actual value roundTripTime = (IE value * 0.0625) + 876
	roundTripTime						INTEGER (0.. 32766)					OPTIONAL
}

UE-Positioning-OTDOA-NeighbourCellList ::= SEQUENCE (SIZE (1..maxCellMeas)) OF
											UE-Positioning-OTDOA-NeighbourCellInfo

UE-Positioning-OTDOA-NeighbourCellList-UEB ::= SEQUENCE (SIZE (1..maxCellMeas)) OF
											UE-Positioning-OTDOA-NeighbourCellInfo-UEB

UE-Positioning-OTDOA-Quality ::=			SEQUENCE {
	stdResolution						BIT STRING (SIZE (2)),
	numberOfOTDOA-Measurements			BIT STRING (SIZE (3)),
	stdOfOTDOA-Measurements				BIT STRING (SIZE (5))
}

UE-Positioning-OTDOA-ReferenceCellInfo ::=			SEQUENCE {
	sfn									INTEGER (0..4095)									OPTIONAL,
	modeSpecificInfo CHOICE {
		fdd										SEQUENCE {
			primaryCPICH-Info					PrimaryCPICH-Info
		},
		tdd										SEQUENCE{
			cellAndChannelIdentity				CellAndChannelIdentity
		}
	},
	frequencyInfo						FrequencyInfo						OPTIONAL,
	positioningMode CHOICE {
		ueBased									SEQUENCE {},
		ueAssisted								SEQUENCE {}
	},
	ue-positioning-IPDL-Paremeters				UE-Positioning-IPDL-Parameters	OPTIONAL
}

UE-Positioning-OTDOA-ReferenceCellInfo-UEB ::=		SEQUENCE {
	sfn									INTEGER (0..4095)									OPTIONAL,
	modeSpecificInfo CHOICE {
		fdd										SEQUENCE {
			primaryCPICH-Info					PrimaryCPICH-Info
		},
		tdd										SEQUENCE{
			cellAndChannelIdentity				CellAndChannelIdentity
		}
	},
	frequencyInfo						FrequencyInfo						OPTIONAL,
	cellPosition						ReferenceCellPosition				OPTIONAL,
	-- Actual value roundTripTime = (IE value * 0.0625) + 876
	roundTripTime						INTEGER (0..32766)					OPTIONAL,
	ue-positioning-IPDL-Paremeters		UE-Positioning-IPDL-Parameters		OPTIONAL
}

UE-Positioning-PositionEstimateInfo ::=					SEQUENCE {
	referenceTime						CHOICE {
		utran-GPSReferenceTimeResult		UTRAN-GPSReferenceTimeResult,
		gps-ReferenceTimeOnly				INTEGER (0..604799999),
		cell-Timing							SEQUENCE {
			sfn									INTEGER (0..4095),
			modeSpecificInfo CHOICE {
				fdd										SEQUENCE {
					primaryCPICH-Info					PrimaryCPICH-Info
				},
				tdd										SEQUENCE{
					cellAndChannelIdentity				CellAndChannelIdentity
				}
			}
		}
	},
	positionEstimate					PositionEstimate
}

UE-Positioning-ReportCriteria ::=				CHOICE {
	ue-positioning-ReportingCriteria				UE-Positioning-EventParamList,
	periodicalReportingCriteria			PeriodicalReportingCriteria,
	noReporting							NULL
}

UE-Positioning-ReportingQuantity ::=			SEQUENCE {
	methodType							UE-Positioning-MethodType,
	positioningMethod					PositioningMethod,
	-- dummy1 is not used in this version of specification and it should
	-- be ignored.
	dummy1								UE-Positioning-ResponseTime,
	horizontal-Accuracy					UE-Positioning-Accuracy				OPTIONAL,
	gps-TimingOfCellWanted				BOOLEAN,
	-- dummy2 is not used in this version of specification and it should
	-- be ignored.
	dummy2								BOOLEAN,
	additionalAssistanceDataRequest		BOOLEAN,
	environmentCharacterisation			EnvironmentCharacterisation			OPTIONAL
}

UE-Positioning-ReportingQuantity-v390ext ::=		SEQUENCE {
	vertical-Accuracy					UE-Positioning-Accuracy
}

UE-Positioning-ResponseTime ::=				ENUMERATED {
										s1, s2, s4, s8, s16,
										s32, s64, s128 }

-- SPARE: UTRA-CarrierRSSI, Max = 76
-- Values above Max are spare
UTRA-CarrierRSSI ::=				INTEGER (0..127)

UTRAN-GPS-DriftRate ::=				ENUMERATED {
									utran-GPSDrift0, utran-GPSDrift1, utran-GPSDrift2,
									utran-GPSDrift5, utran-GPSDrift10, utran-GPSDrift15,
									utran-GPSDrift25, utran-GPSDrift50, utran-GPSDrift-1,
									utran-GPSDrift-2, utran-GPSDrift-5, utran-GPSDrift-10,
									utran-GPSDrift-15, utran-GPSDrift-25, utran-GPSDrift-50}

UTRAN-GPSReferenceTime ::=			SEQUENCE {
	-- For utran-GPSTimingOfCell values above 2322431999999 are not
	-- used in this version of the specification
	-- Actual value utran-GPSTimingOfCell = (ms-part * 4294967296) + ls-part
	utran-GPSTimingOfCell			SEQUENCE {
		ms-part 						INTEGER (0..1023),
		ls-part							INTEGER (0..4294967295)
	},
	modeSpecificInfo				CHOICE {
		fdd								SEQUENCE {
			referenceIdentity				PrimaryCPICH-Info
		},
		tdd								SEQUENCE {
			referenceIdentity				CellParametersID
		}
	}			OPTIONAL,
	sfn									INTEGER (0..4095)
}

UTRAN-GPSReferenceTimeResult ::=	SEQUENCE {
	-- For ue-GPSTimingOfCell values above 37158911999999 are not
	-- used in this version of the specification
	-- Actual value ue-GPSTimingOfCell = (ms-part * 4294967296) + ls-part
	ue-GPSTimingOfCell			SEQUENCE {
		ms-part 						INTEGER (0..16383),
		ls-part							INTEGER (0..4294967295)
	},
	modeSpecificInfo				CHOICE {
		fdd								SEQUENCE {
			referenceIdentity				PrimaryCPICH-Info
		},
		tdd								SEQUENCE {
			referenceIdentity				CellParametersID
		}
	},
	sfn							INTEGER (0..4095)
}

VarianceOfRLC-BufferPayload ::=		ENUMERATED {
										plv0, plv4, plv8, plv16, plv32, plv64,
										plv128, plv256, plv512, plv1024,
										plv2k, plv4k, plv8k, plv16k, spare2, spare1 }

-- Actual value W = IE value * 0.1
W ::=								INTEGER (0..20)

-- ***************************************************
--
--     OTHER INFORMATION ELEMENTS (10.3.8)
--
-- ***************************************************

BCC ::=								INTEGER (0..7)

BCCH-ModificationInfo ::=			SEQUENCE {
	mib-ValueTag						MIB-ValueTag,
	bcch-ModificationTime				BCCH-ModificationTime				OPTIONAL
}

-- Actual value BCCH-ModificationTime = IE value * 8
BCCH-ModificationTime ::=			INTEGER (0..511)

BSIC ::=							SEQUENCE {
	ncc									NCC,
	bcc									BCC
}

CBS-DRX-Level1Information ::=		SEQUENCE {
	ctch-AllocationPeriod				INTEGER (1..256),
	cbs-FrameOffset						INTEGER (0..255)
}

CDMA2000-Message ::=				SEQUENCE {
	msg-Type							BIT STRING (SIZE (8)),
	payload								BIT STRING (SIZE (1..512))
}

CDMA2000-MessageList ::=				SEQUENCE (SIZE (1..maxInterSysMessages)) OF
											CDMA2000-Message

CDMA2000-UMTS-Frequency-List	::=		SEQUENCE (SIZE (1..maxNumCDMA2000Freqs)) OF
											FrequencyInfoCDMA2000

CellValueTag ::=						INTEGER (1..4)

--Actual value = 2^(IE value)
ExpirationTimeFactor			::=		INTEGER (1..8)

FDD-UMTS-Frequency-List			::=		SEQUENCE (SIZE (1..maxNumFDDFreqs)) OF
											FrequencyInfoFDD

FrequencyInfoCDMA2000			::=		SEQUENCE {
											band-Class		BIT STRING (SIZE (5)),
											cdma-Freq		BIT STRING (SIZE(11))
}

GSM-BA-Range					::=	SEQUENCE {
											gsmLowRangeUARFCN		UARFCN,
											gsmUpRangeUARFCN		UARFCN
}

GSM-BA-Range-List				::=	SEQUENCE (SIZE (1..maxNumGSMFreqRanges)) OF
											GSM-BA-Range

-- This IE is formatted as 'TLV' and is coded in the same way as the Mobile Station Classmark 2 
-- information element in [5]. The first octet is the Mobile station classmark 2 IEI and its value
-- shall be set to 33H. The second octet is the Length of mobile station classmark 2 and its value 
-- shall be set to 3. The octet 3 contains the first octet of the value part of the Mobile Station 
-- Classmark 2 information element, the octet 4 contains the second octet of the value part of the 
-- Mobile Station Classmark 2 information element and so on. For each of these octets, the first/
-- leftmost/ most significant bit of the octet contains b8 of the corresponding octet of the Mobile
-- Station Classmark 2.
GSM-Classmark2::=					OCTET STRING (SIZE (5))

-- This IE is formatted as 'V' and is coded in the same way as the value part in the Mobile station
-- classmark 3 information element in [5].
-- The value part is specified by means of CSN.1, which encoding results in a bit string, to which
-- final padding may be appended upto the next octet boundary [5]. The first/ leftmost bit of the
-- CSN.1 bit string is placed in the first/ leftmost/ most significant bit of the first
-- octet. This continues until the last bit of the CSN.1 bit string, which is placed in the last/
-- rightmost/ least significant bit of the last octet.
GSM-Classmark3::=					OCTET STRING (SIZE (1..32))

GSM-MessageList ::=					SEQUENCE (SIZE (1..maxInterSysMessages)) OF
										BIT STRING (SIZE (1..512))

GsmSecurityCapability ::=			BIT STRING {
										-- For each bit value "0" means false/ not supported
										a5-7(0),
										a5-6(1),
										a5-5(2),
										a5-4(3),
										a5-3(4),
										a5-2(5),
										a5-1(6)
										}	(SIZE (7))

IdentificationOfReceivedMessage ::=	SEQUENCE {
		rrc-TransactionIdentifier		RRC-TransactionIdentifier,
		receivedMessageType				ReceivedMessageType
}

InterRAT-ChangeFailureCause ::=		CHOICE {
	configurationUnacceptable			NULL,
	physicalChannelFailure				NULL,
	protocolError						ProtocolErrorInformation,
	unspecified							NULL,
	spare4								NULL,
	spare3								NULL,
	spare2								NULL,
	spare1								NULL
}							

InterRAT-UE-RadioAccessCapability ::= CHOICE {
	gsm									SEQUENCE {
		gsm-Classmark2						GSM-Classmark2,
		gsm-Classmark3						GSM-Classmark3
	},
	cdma2000							SEQUENCE {
		cdma2000-MessageList				CDMA2000-MessageList
	}
}

InterRAT-UE-RadioAccessCapabilityList ::=	SEQUENCE (SIZE(1..maxInterSysMessages)) OF
											InterRAT-UE-RadioAccessCapability

InterRAT-UE-SecurityCapability ::= CHOICE {
	gsm									SEQUENCE {
		gsmSecurityCapability			GsmSecurityCapability
	}
}

InterRAT-UE-SecurityCapList ::=	SEQUENCE (SIZE(1..maxInterSysMessages)) OF
										InterRAT-UE-SecurityCapability

InterRAT-HO-FailureCause ::=		CHOICE {
	configurationUnacceptable			NULL,
	physicalChannelFailure				NULL,
	protocolError						ProtocolErrorInformation,
	interRAT-ProtocolError				NULL,
	unspecified							NULL,
	spare11								NULL,
	spare10								NULL,
	spare9								NULL,
	spare8								NULL,
	spare7								NULL,
	spare6								NULL,
	spare5								NULL,
	spare4								NULL,
	spare3								NULL,
	spare2								NULL,
	spare1								NULL
}							

MasterInformationBlock ::=			SEQUENCE {
		mib-ValueTag					MIB-ValueTag,
		-- TABULAR: The PLMN identity and ANSI-41 core network information
		-- are included in PLMN-Type.
		plmn-Type						PLMN-Type,
		sibSb-ReferenceList				SIBSb-ReferenceList,
	-- Extension mechanism for non- release99 information
		nonCriticalExtensions			SEQUENCE {}							OPTIONAL
}

MIB-ValueTag ::=					INTEGER (1..8)

NCC ::=								INTEGER (0..7)

PLMN-ValueTag ::=					INTEGER (1..256)


PredefinedConfigIdentityAndValueTag ::=	SEQUENCE {
	predefinedConfigIdentity				PredefinedConfigIdentity,
	predefinedConfigValueTag				PredefinedConfigValueTag
}

ProtocolErrorInformation ::=		SEQUENCE {
	diagnosticsType						CHOICE {
		type1								SEQUENCE {
			protocolErrorCause					ProtocolErrorCause
		},
		spare								NULL
	}
}

ReceivedMessageType ::=				ENUMERATED {
										activeSetUpdate,
										cellChangeOrderFromUTRAN,
										cellUpdateConfirm,
										counterCheck,
										downlinkDirectTransfer,
										interRATHandoverCommand,
										measurementControl,
										pagingType2,
										physicalChannelReconfiguration,
										physicalSharedChannelAllocation,
										radioBearerReconfiguration,
										radioBearerRelease,
										radioBearerSetup,
										rrcConnectionRelease,
										rrcConnectionReject,
										rrcConnectionSetup,
										securityModeCommand,
										signallingConnectionRelease,
										transportChannelReconfiguration,
										transportFormatCombinationControl,
										ueCapabilityEnquiry,
										ueCapabilityInformationConfirm,
										uplinkPhysicalChannelControl,
										uraUpdateConfirm,
										utranMobilityInformation,
										assistanceDataDelivery,
										spare6, spare5, spare4, spare3,
										spare2, spare1 }

Rplmn-Information				::=		SEQUENCE {
											gsm-BA-Range-List		GSM-BA-Range-List	OPTIONAL,
											fdd-UMTS-Frequency-List	FDD-UMTS-Frequency-List	OPTIONAL,
											tdd-UMTS-Frequency-List	TDD-UMTS-Frequency-List	OPTIONAL,
											cdma2000-UMTS-Frequency-List	CDMA2000-UMTS-Frequency-List	OPTIONAL
}

SchedulingInformation ::=			SEQUENCE {
	scheduling							SEQUENCE {
		segCount							SegCount						DEFAULT 1,
		sib-Pos								CHOICE {
			-- The element name indicates the repetition period and the value
			-- (multiplied by two) indicates the position of the first segment.
			rep4								INTEGER (0..1),
			rep8								INTEGER (0..3),
			rep16								INTEGER (0..7),
			rep32								INTEGER (0..15),
			rep64								INTEGER (0..31),
			rep128								INTEGER (0..63),
			rep256								INTEGER (0..127),
			rep512								INTEGER (0..255),
			rep1024								INTEGER (0..511),
			rep2048								INTEGER (0..1023),
			rep4096								INTEGER (0..2047)
		},
		sib-PosOffsetInfo					SibOFF-List						OPTIONAL
	}
}

SchedulingInformationSIB ::=			SEQUENCE {
	sib-Type							SIB-TypeAndTag,
	scheduling							SchedulingInformation
}

SchedulingInformationSIBSb ::=			SEQUENCE {
	sibSb-Type							SIBSb-TypeAndTag,
	scheduling							SchedulingInformation
}

SegCount ::=						INTEGER (1..16)

SegmentIndex ::=					INTEGER (1..15)

-- Actual value SFN-Prime = 2 * IE value
SFN-Prime ::=						INTEGER (0..2047)


SIB-Data-fixed ::=					BIT STRING (SIZE (222))


SIB-Data-variable ::=				BIT STRING (SIZE (1..214))

SIBOccurIdentity ::=			INTEGER (0..15)

SIBOccurrenceIdentityAndValueTag ::=	SEQUENCE {
	sibOccurIdentity				SIBOccurIdentity,
	sibOccurValueTag				SIBOccurValueTag
}

SIBOccurValueTag ::=			INTEGER (0..15)

SIB-ReferenceList ::=				SEQUENCE (SIZE (1..maxSIB)) OF
										SchedulingInformationSIB

SIBSb-ReferenceList ::=				SEQUENCE (SIZE (1..maxSIB)) OF
										SchedulingInformationSIBSb

SIB-ReferenceListFACH ::=			SEQUENCE (SIZE (1..maxSIB-FACH)) OF
										SchedulingInformationSIB

SIB-Type ::=						ENUMERATED {
										masterInformationBlock,
										systemInformationBlockType1,
										systemInformationBlockType2,
										systemInformationBlockType3,
										systemInformationBlockType4,
										systemInformationBlockType5,
										systemInformationBlockType6,
										systemInformationBlockType7,
										systemInformationBlockType8,
										systemInformationBlockType9,
										systemInformationBlockType10,
										systemInformationBlockType11,
										systemInformationBlockType12,
										systemInformationBlockType13,
										systemInformationBlockType13-1,
										systemInformationBlockType13-2,
										systemInformationBlockType13-3,
										systemInformationBlockType13-4,
										systemInformationBlockType14,
										systemInformationBlockType15,
										systemInformationBlockType15-1,
										systemInformationBlockType15-2,
										systemInformationBlockType15-3,
										systemInformationBlockType16,
										systemInformationBlockType17,
										systemInformationBlockType15-4,
										systemInformationBlockType18,
										schedulingBlock1,
										schedulingBlock2,
										systemInformationBlockType15-5,
										spare1, spare2 }

SIB-TypeAndTag ::=					CHOICE {
	sysInfoType1						PLMN-ValueTag,
	sysInfoType2						CellValueTag,
	sysInfoType3						CellValueTag,
	sysInfoType4						CellValueTag,
	sysInfoType5						CellValueTag,
	sysInfoType6						CellValueTag,
	sysInfoType7						NULL,
	sysInfoType8						CellValueTag,
	sysInfoType9						NULL,
	sysInfoType10						NULL,
	sysInfoType11						CellValueTag,
	sysInfoType12						CellValueTag,
	sysInfoType13						CellValueTag,
	sysInfoType13-1						CellValueTag,
	sysInfoType13-2						CellValueTag,
	sysInfoType13-3						CellValueTag,
	sysInfoType13-4						CellValueTag,
	sysInfoType14						NULL,
	sysInfoType15						CellValueTag,
	sysInfoType16						PredefinedConfigIdentityAndValueTag,
	sysInfoType17						NULL,
	sysInfoType15-1						CellValueTag,
	sysInfoType15-2						SIBOccurrenceIdentityAndValueTag,
	sysInfoType15-3						SIBOccurrenceIdentityAndValueTag,
	sysInfoType15-4						CellValueTag,
	sysInfoType18						CellValueTag,
	sysInfoType15-5						CellValueTag,
	spare5								NULL,
	spare4								NULL,
	spare3								NULL,
	spare2								NULL,
	spare1								NULL
}

SIBSb-TypeAndTag ::=					CHOICE {
	sysInfoType1						PLMN-ValueTag,
	sysInfoType2						CellValueTag,
	sysInfoType3						CellValueTag,
	sysInfoType4						CellValueTag,
	sysInfoType5						CellValueTag,
	sysInfoType6						CellValueTag,
	sysInfoType7						NULL,
	sysInfoType8						CellValueTag,
	sysInfoType9						NULL,
	sysInfoType10						NULL,
	sysInfoType11						CellValueTag,
	sysInfoType12						CellValueTag,
	sysInfoType13						CellValueTag,
	sysInfoType13-1						CellValueTag,
	sysInfoType13-2						CellValueTag,
	sysInfoType13-3						CellValueTag,
	sysInfoType13-4						CellValueTag,
	sysInfoType14						NULL,
	sysInfoType15						CellValueTag,
	sysInfoType16						PredefinedConfigIdentityAndValueTag,
	sysInfoType17						NULL,
	sysInfoTypeSB1						CellValueTag,
	sysInfoTypeSB2						CellValueTag,
	sysInfoType15-1						CellValueTag,
	sysInfoType15-2						SIBOccurrenceIdentityAndValueTag,
	sysInfoType15-3						SIBOccurrenceIdentityAndValueTag,
	sysInfoType15-4						CellValueTag,
	sysInfoType18						CellValueTag,
	sysInfoType15-5						CellValueTag,
	spare3								NULL,
	spare2								NULL,
	spare1								NULL
}

SibOFF ::=							ENUMERATED {
										so2, so4, so6, so8, so10,
										so12, so14, so16, so18,
										so20, so22, so24, so26,
										so28, so30, so32 }

SibOFF-List ::=						SEQUENCE (SIZE (1..15)) OF
										SibOFF

SysInfoType1 ::=					SEQUENCE {
	-- Core network IEs
		cn-CommonGSM-MAP-NAS-SysInfo	NAS-SystemInformationGSM-MAP,	
		cn-DomainSysInfoList			CN-DomainSysInfoList,
	-- User equipment IEs
		ue-ConnTimersAndConstants		UE-ConnTimersAndConstants			OPTIONAL,
		ue-IdleTimersAndConstants		UE-IdleTimersAndConstants			OPTIONAL,
	-- Extension mechanism for non- release99 information
		v3a0NonCriticalExtensions		SEQUENCE {
			sysInfoType1-v3a0ext			SysInfoType1-v3a0ext-IEs,
			nonCriticalExtensions			SEQUENCE {} OPTIONAL
		}	OPTIONAL
}

SysInfoType1-v3a0ext-IEs ::= 		SEQUENCE {
	ue-ConnTimersAndConstants-v3a0ext		UE-ConnTimersAndConstants-v3a0ext,
	ue-IdleTimersAndConstants-v3a0ext		UE-IdleTimersAndConstants-v3a0ext
}

SysInfoType2 ::=					SEQUENCE {
	-- UTRAN mobility IEs
		ura-IdentityList				URA-IdentityList,
	-- Extension mechanism for non- release99 information
		nonCriticalExtensions			SEQUENCE {}							OPTIONAL
}

SysInfoType3 ::=					SEQUENCE {
		sib4indicator					BOOLEAN,
	-- UTRAN mobility IEs
		cellIdentity					CellIdentity,
		cellSelectReselectInfo			CellSelectReselectInfoSIB-3-4,
		cellAccessRestriction			CellAccessRestriction,
	-- Extension mechanism for non- release99 information
		nonCriticalExtensions			SEQUENCE {}							OPTIONAL
}

SysInfoType4 ::=					SEQUENCE {
	-- UTRAN mobility IEs
		cellIdentity					CellIdentity,
		cellSelectReselectInfo			CellSelectReselectInfoSIB-3-4,
		cellAccessRestriction			CellAccessRestriction,
	-- Extension mechanism for non- release99 information
		nonCriticalExtensions			SEQUENCE {}							OPTIONAL
}

SysInfoType5 ::=					SEQUENCE {
		sib6indicator					BOOLEAN,
	-- Physical channel IEs
		pich-PowerOffset				PICH-PowerOffset,
		modeSpecificInfo				CHOICE {
			fdd								SEQUENCE {
				aich-PowerOffset				AICH-PowerOffset
			},
			tdd								SEQUENCE {
				pusch-SysInfoList-SFN			PUSCH-SysInfoList-SFN		OPTIONAL,
				pdsch-SysInfoList-SFN			PDSCH-SysInfoList-SFN		OPTIONAL,
				openLoopPowerControl-TDD		OpenLoopPowerControl-TDD
	}
		},
		primaryCCPCH-Info				PrimaryCCPCH-Info					OPTIONAL,
		prach-SystemInformationList		PRACH-SystemInformationList,
		sCCPCH-SystemInformationList	SCCPCH-SystemInformationList,
		-- cbs-DRX-Level1Information is conditional on any of the CTCH indicator IEs in
		-- sCCPCH-SystemInformationList
		cbs-DRX-Level1Information		CBS-DRX-Level1Information			OPTIONAL,
	-- Extension mechanism for non- release99 information
		nonCriticalExtensions			SEQUENCE {}							OPTIONAL
}

SysInfoType6 ::=					SEQUENCE {
	-- Physical channel IEs
		pich-PowerOffset				PICH-PowerOffset,
		modeSpecificInfo				CHOICE {
			fdd								SEQUENCE {
				aich-PowerOffset				AICH-PowerOffset,
				-- dummy is not used in this version of specification, it should
				-- not be sent and if received it should be ignored.
				dummy				CSICH-PowerOffset			OPTIONAL

			},
			tdd								SEQUENCE {
				pusch-SysInfoList-SFN			PUSCH-SysInfoList-SFN		OPTIONAL,
				pdsch-SysInfoList-SFN			PDSCH-SysInfoList-SFN		OPTIONAL,
				openLoopPowerControl-TDD		OpenLoopPowerControl-TDD
			}
		},
		primaryCCPCH-Info				PrimaryCCPCH-Info					OPTIONAL,
		prach-SystemInformationList		PRACH-SystemInformationList			OPTIONAL,
		sCCPCH-SystemInformationList	SCCPCH-SystemInformationList		OPTIONAL,
		-- cbs-DRX-Level1Information is conditional on any of the CTCH indicator IEs in
		-- sCCPCH-SystemInformationList
		cbs-DRX-Level1Information		CBS-DRX-Level1Information			OPTIONAL,
	-- Extension mechanism for non- release99 information
		nonCriticalExtensions			SEQUENCE {}							OPTIONAL
}

SysInfoType7 ::=					SEQUENCE {
	-- Physical channel IEs
		modeSpecificInfo				CHOICE {
			fdd								SEQUENCE {
				ul-Interference					UL-Interference
			},
			tdd								NULL
		},
		prach-Information-SIB5-List		DynamicPersistenceLevelList,
		prach-Information-SIB6-List		DynamicPersistenceLevelList			OPTIONAL,
		expirationTimeFactor			ExpirationTimeFactor				OPTIONAL,
	-- Extension mechanism for non- release99 information
		nonCriticalExtensions			SEQUENCE {}							OPTIONAL
}

SysInfoType8 ::=					SEQUENCE {
	-- User equipment IEs
		cpch-Parameters					CPCH-Parameters,
	-- Physical channel IEs
		cpch-SetInfoList				CPCH-SetInfoList,
		csich-PowerOffset				CSICH-PowerOffset,
	-- Extension mechanism for non- release99 information
		nonCriticalExtensions			SEQUENCE {}							OPTIONAL
}

SysInfoType9 ::=					SEQUENCE {
	-- Physical channel IEs
		cpch-PersistenceLevelsList		CPCH-PersistenceLevelsList,
	-- Extension mechanism for non- release99 information
		nonCriticalExtensions			SEQUENCE {}							OPTIONAL
}

SysInfoType10 ::=					SEQUENCE {
	-- User equipment IEs
		drac-SysInfoList				DRAC-SysInfoList,
	-- Extension mechanism for non- release99 information
		nonCriticalExtensions			SEQUENCE {}							OPTIONAL
}

SysInfoType11 ::=					SEQUENCE {
		sib12indicator					BOOLEAN,
	-- Measurement IEs
		fach-MeasurementOccasionInfo	FACH-MeasurementOccasionInfo		OPTIONAL,
		measurementControlSysInfo		MeasurementControlSysInfo,
	-- Extension mechanism for non- release99 information
		nonCriticalExtensions			SEQUENCE {}							OPTIONAL
}

SysInfoType12 ::=					SEQUENCE {
	-- Measurement IEs
		fach-MeasurementOccasionInfo	FACH-MeasurementOccasionInfo		OPTIONAL,
		measurementControlSysInfo		MeasurementControlSysInfo,
	-- Extension mechanism for non- release99 information
		nonCriticalExtensions			SEQUENCE {}							OPTIONAL
}

SysInfoType13 ::=					SEQUENCE {
	-- Core network IEs
		cn-DomainSysInfoList			CN-DomainSysInfoList,
	-- User equipment IEs
		ue-IdleTimersAndConstants		UE-IdleTimersAndConstants			OPTIONAL,
		capabilityUpdateRequirement		CapabilityUpdateRequirement			OPTIONAL,
	-- Extension mechanism for non- release99 information
		v3a0NonCriticalExtensions		SEQUENCE {
			sysInfoType13-v3a0ext			SysInfoType13-v3a0ext-IEs,
			nonCriticalExtensions			SEQUENCE {} OPTIONAL
		}	OPTIONAL
}

SysInfoType13-v3a0ext-IEs ::= SEQUENCE {
	ue-IdleTimersAndConstants-v3a0ext		UE-IdleTimersAndConstants-v3a0ext
}

SysInfoType13-1 ::=					SEQUENCE {
	-- ANSI-41 IEs
		ansi-41-RAND-Information		ANSI-41-RAND-Information,
	-- Extension mechanism for non- release99 information
		nonCriticalExtensions			SEQUENCE {}							OPTIONAL
}

SysInfoType13-2 ::=					SEQUENCE {
	-- ANSI-41 IEs
		ansi-41-UserZoneID-Information	ANSI-41-UserZoneID-Information,
	-- Extension mechanism for non- release99 information
		nonCriticalExtensions			SEQUENCE {}							OPTIONAL
}

SysInfoType13-3 ::=					SEQUENCE {
	-- ANSI-41 IEs
		ansi-41-PrivateNeighbourListInfo ANSI-41-PrivateNeighbourListInfo,
	-- Extension mechanism for non- release99 information
		nonCriticalExtensions			SEQUENCE {}							OPTIONAL
}

SysInfoType13-4 ::=					SEQUENCE {
	-- ANSI-41 IEs
		ansi-41-GlobalServiceRedirectInfo
										ANSI-41-GlobalServiceRedirectInfo,
	-- Extension mechanism for non- release99 information
		nonCriticalExtensions			SEQUENCE {}							OPTIONAL
}

SysInfoType14 ::=					SEQUENCE {
	-- Physical channel IEs
		individualTS-InterferenceList	IndividualTS-InterferenceList,
		expirationTimeFactor			ExpirationTimeFactor				OPTIONAL,
	-- Extension mechanism for non- release99 information
		nonCriticalExtensions			SEQUENCE {}							OPTIONAL
}


SysInfoType15 ::=					SEQUENCE {
	-- Measurement IEs		
		ue-positioning-GPS-CipherParameters		UE-Positioning-CipherParameters		OPTIONAL,
		ue-positioning-GPS-ReferenceLocation	ReferenceLocation,
		ue-positioning-GPS-ReferenceTime		UE-Positioning-GPS-ReferenceTime,
		ue-positioning-GPS-Real-timeIntegrity		BadSatList							OPTIONAL,
	-- Extension mechanism for non- release99 information
		nonCriticalExtensions			SEQUENCE {}							OPTIONAL
}

SysInfoType15-1 ::=					SEQUENCE {
	-- DGPS corrections
		ue-positioning-GPS-DGPS-Corrections			UE-Positioning-GPS-DGPS-Corrections,
	-- Extension mechanism for non- release99 information
		nonCriticalExtensions			SEQUENCE {}				OPTIONAL
}

SysInfoType15-2 ::=					SEQUENCE {
	-- Ephemeris and clock corrections
		transmissionTOW					INTEGER (0..604799),
		satID							SatID,
		ephemerisParameter				EphemerisParameter,
	-- Extension mechanism for non- release99 information
		nonCriticalExtensions			SEQUENCE {}			OPTIONAL
}

SysInfoType15-3 ::=					SEQUENCE {
	-- Almanac and other data
		transmissionTOW					INTEGER (0.. 604799),
		ue-positioning-GPS-Almanac					UE-Positioning-GPS-Almanac				OPTIONAL,
		ue-positioning-GPS-IonosphericModel			UE-Positioning-GPS-IonosphericModel		OPTIONAL,
		ue-positioning-GPS-UTC-Model				UE-Positioning-GPS-UTC-Model			OPTIONAL,
		satMask							BIT STRING (SIZE (1..32))	OPTIONAL,
		lsbTOW							BIT STRING (SIZE (8))		OPTIONAL,
	-- Extension mechanism for non- release99 information
		nonCriticalExtensions			SEQUENCE {}					OPTIONAL
}

SysInfoType15-4 ::=					SEQUENCE {
	-- Measurement IEs
		ue-positioning-OTDOA-CipherParameters	UE-Positioning-CipherParameters			OPTIONAL,
		ue-positioning-OTDOA-AssistanceData		UE-Positioning-OTDOA-AssistanceData,
		v3a0NonCriticalExtensions			SEQUENCE {
			sysInfoType15-4-v3a0ext				SysInfoType15-4-v3a0ext,
		-- Extension mechanism for non- release99 information
			nonCriticalExtensions		SEQUENCE {}						OPTIONAL
		}	OPTIONAL
}

SysInfoType15-4-v3a0ext ::= 		SEQUENCE {
	sfn-Offset-Validity					SFN-Offset-Validity		OPTIONAL
}

SysInfoType15-5 ::=					SEQUENCE {
	-- Measurement IEs
		ue-positioning-OTDOA-AssistanceData-UEB		UE-Positioning-OTDOA-AssistanceData-UEB,
		v3a0NonCriticalExtensions			SEQUENCE {
			sysInfoType15-5-v3a0ext				SysInfoType15-5-v3a0ext,
		-- Extension mechanism for non- release99 information
			nonCriticalExtensions		SEQUENCE {}						OPTIONAL
		}	OPTIONAL
}

SysInfoType15-5-v3a0ext ::= 		SEQUENCE {
	sfn-Offset-Validity					SFN-Offset-Validity		OPTIONAL
}

SysInfoType16 ::=					SEQUENCE {
	-- Radio bearer IEs
		preDefinedRadioConfiguration	PreDefRadioConfiguration,
	-- Extension mechanism for non- release99 information
		nonCriticalExtensions			SEQUENCE {}							OPTIONAL
}

SysInfoType17 ::=					SEQUENCE {
	-- Physical channel IEs
		pusch-SysInfoList				PUSCH-SysInfoList				OPTIONAL,
		pdsch-SysInfoList				PDSCH-SysInfoList				OPTIONAL,
	-- Extension mechanism for non- release99 information
		nonCriticalExtensions			SEQUENCE {}							OPTIONAL
}

SysInfoType18 ::=						SEQUENCE {
		idleModePLMNIdentities			PLMNIdentitiesOfNeighbourCells		OPTIONAL,
		connectedModePLMNIdentities	PLMNIdentitiesOfNeighbourCells		OPTIONAL,
	-- Extension mechanism for non- release99 information
		nonCriticalExtensions			SEQUENCE {}		OPTIONAL
}

SysInfoTypeSB1 ::=					SEQUENCE {
	-- Other IEs
		sib-ReferenceList				SIB-ReferenceList,
	-- Extension mechanism for non- release99 information
		nonCriticalExtensions			SEQUENCE {}							OPTIONAL
}

SysInfoTypeSB2 ::=					SEQUENCE {
	-- Other IEs
		sib-ReferenceList				SIB-ReferenceList,
	-- Extension mechanism for non- release99 information
		nonCriticalExtensions			SEQUENCE {}							OPTIONAL
}
TDD-UMTS-Frequency-List	::=			SEQUENCE (SIZE (1..maxNumTDDFreqs)) OF
											FrequencyInfoTDD

-- ***************************************************
--
--     ANSI-41 INFORMATION ELEMENTS (10.3.9)
--
-- ***************************************************

ANSI-41-GlobalServiceRedirectInfo ::=	ANSI-41-NAS-Parameter
ANSI-41-PrivateNeighbourListInfo ::=	ANSI-41-NAS-Parameter
ANSI-41-RAND-Information ::=			ANSI-41-NAS-Parameter
ANSI-41-UserZoneID-Information ::=		ANSI-41-NAS-Parameter
ANSI-41-NAS-Parameter ::=				BIT STRING (SIZE (1..2048))

Min-P-REV ::=							BIT STRING (SIZE (8))

NAS-SystemInformationANSI-41 ::=		ANSI-41-NAS-Parameter
NID ::=									BIT STRING (SIZE (16))

P-REV ::=								BIT STRING (SIZE (8))

SID ::=									BIT STRING (SIZE (15))

END
